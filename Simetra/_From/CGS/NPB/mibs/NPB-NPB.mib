NPB-NPB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    cgs
        FROM CGS
;

npb MODULE-IDENTITY
    LAST-UPDATED "201607100000Z"
    ORGANIZATION "@ORGANIZATION"
    CONTACT-INFO "@CONTACT-INFO"
    DESCRIPTION "This module is the parent module for all NPB applications"
    REVISION "201607100000Z"
    DESCRIPTION "@REVISION-DESCRIPTION"
    ::= { cgs 100 }

END
