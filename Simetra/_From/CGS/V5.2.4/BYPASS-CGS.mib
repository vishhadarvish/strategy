--
-- OTS3000-BPS-8L.my
-- MIB generated by MG-SOFT Visual MIB Builder Version 6.0  Build 88
-- Monday, June 13, 2016 at 11:45:50
--
	OTS3000-BPS-8L DEFINITIONS ::= BEGIN
 
		IMPORTS
			enterprises, IpAddress, OBJECT-TYPE, MODULE-IDENTITY, TimeTicks		
				FROM SNMPv2-SMI;
	
	
		-- 1.3.6.1.4.1.47477
		cgs MODULE-IDENTITY 
			LAST-UPDATED "202309141830Z"		
			ORGANIZATION 
				"GLSUN  Corporation"
			CONTACT-INFO 
				""
			DESCRIPTION 
				""
			REVISION "SV1.02.23Z"		 
			DESCRIPTION 
				""
			::= { enterprises 47477 }

		
	
--
-- Node definitions
--
	
		-- 1.3.6.1.4.1.47477.10
		EBP-1U2U4U OBJECT IDENTIFIER ::= { cgs 10 }

		
		-- 1.3.6.1.4.1.47477.10.21
		bypass OBJECT IDENTIFIER ::= { EBP-1U2U4U 21 }
          
     		
		
		-- 1.3.6.1.4.1.47477.10.21.60
		nmu OBJECT IDENTIFIER ::= { bypass 60 }

		-- 1.3.6.1.4.1.47477.10.21.20.50		
		nmuTrap OBJECT IDENTIFIER ::= { nmu 50 }
		
		
		--link1
		-- 1.3.6.1.4.1.47477.10.21.1
		link1 OBJECT IDENTIFIER ::= { bypass 1 }
		
		-- 1.3.6.1.4.1.47477.10.21.1.3
		link1OBP OBJECT IDENTIFIER ::= { link1 3 }

		-- 1.3.6.1.4.1.47477.10.21.1.3.50		
		link1OBPTrap OBJECT IDENTIFIER ::= { link1OBP 50 }
 		
		
		-- link2
		-- 1.3.6.1.4.1.47477.10.21.2
		link2 OBJECT IDENTIFIER ::= { bypass 2 }

		-- 1.3.6.1.4.1.47477.10.21.2.3
		link2OBP OBJECT IDENTIFIER ::= { link2 3 }
		
		-- 1.3.6.1.4.1.47477.10.21.2.3.50		
		link2OBPTrap OBJECT IDENTIFIER ::= { link2OBP 50 }
		
		
		-- link3
		-- 1.3.6.1.4.1.47477.10.21.3
		link3 OBJECT IDENTIFIER ::= { bypass 3 }

		-- 1.3.6.1.4.1.47477.10.21.3.3
		link3OBP OBJECT IDENTIFIER ::= { link3 3 }
		
		-- 1.3.6.1.4.1.47477.10.21.3.3.50		
		link3OBPTrap OBJECT IDENTIFIER ::= { link3OBP 50 }


		-- link4
		-- 1.3.6.1.4.1.47477.10.21.4
		link4 OBJECT IDENTIFIER ::= { bypass 4 }

		-- 1.3.6.1.4.1.47477.10.21.4.3
		link4OBP OBJECT IDENTIFIER ::= { link4 3 }
		
		-- 1.3.6.1.4.1.47477.10.21.4.3.50		
		link4OBPTrap OBJECT IDENTIFIER ::= { link4OBP 50 }


		-- link5
		-- 1.3.6.1.4.1.47477.10.21.5
		link5 OBJECT IDENTIFIER ::= { bypass 5 }

		-- 1.3.6.1.4.1.47477.10.21.5.3
		link5OBP OBJECT IDENTIFIER ::= { link5 3 }
		
		-- 1.3.6.1.4.1.47477.10.21.5.3.50		
		link5OBPTrap OBJECT IDENTIFIER ::= { link5OBP 50 }
		
		
		-- link6
		-- 1.3.6.1.4.1.47477.10.21.6
		link6 OBJECT IDENTIFIER ::= { bypass 6 }

		-- 1.3.6.1.4.1.47477.10.21.6.3
		link6OBP OBJECT IDENTIFIER ::= { link6 3 }
		
		-- 1.3.6.1.4.1.47477.10.21.6.3.50		
		link6OBPTrap OBJECT IDENTIFIER ::= { link6OBP 50 }

		
		-- link7
		-- 1.3.6.1.4.1.47477.10.21.7
		link7 OBJECT IDENTIFIER ::= { bypass 7 }

		-- 1.3.6.1.4.1.47477.10.21.7.3
		link7OBP OBJECT IDENTIFIER ::= { link7 3 }
		
		-- 1.3.6.1.4.1.47477.10.21.7.3.50		
		link7OBPTrap OBJECT IDENTIFIER ::= { link7OBP 50 }


		-- link8
		-- 1.3.6.1.4.1.47477.10.21.8
		link8 OBJECT IDENTIFIER ::= { bypass 8 }

		-- 1.3.6.1.4.1.47477.10.21.8.3
		link8OBP OBJECT IDENTIFIER ::= { link8 3 }
		
		-- 1.3.6.1.4.1.47477.10.21.8.3.50		
		link8OBPTrap OBJECT IDENTIFIER ::= { link8OBP 50 }
		

		-- link9
		-- 1.3.6.1.4.1.47477.10.21.9
		link9 OBJECT IDENTIFIER ::= { bypass 9 }

		-- 1.3.6.1.4.1.47477.10.21.9.3
		link9OBP OBJECT IDENTIFIER ::= { link9 3 }
		
		-- 1.3.6.1.4.1.47477.10.21.9.3.50		
		link9OBPTrap OBJECT IDENTIFIER ::= { link9OBP 50 }
		

		-- link10
		-- 1.3.6.1.4.1.47477.10.21.10
		link10 OBJECT IDENTIFIER ::= { bypass 10 }

		-- 1.3.6.1.4.1.47477.10.21.10.3
		link10OBP OBJECT IDENTIFIER ::= { link10 3 }
		
		-- 1.3.6.1.4.1.47477.10.21.10.3.50		
		link10OBPTrap OBJECT IDENTIFIER ::= { link10OBP 50 }
				

		-- link11
		-- 1.3.6.1.4.1.47477.10.21.11
		link11 OBJECT IDENTIFIER ::= { bypass 11 }

		-- 1.3.6.1.4.1.47477.10.21.11.3
		link11OBP OBJECT IDENTIFIER ::= { link11 3 }
		
		-- 1.3.6.1.4.1.47477.10.21.11.3.50		
		link11OBPTrap OBJECT IDENTIFIER ::= { link11OBP 50 }
				

		-- link12
		-- 1.3.6.1.4.1.47477.10.21.12
		link12 OBJECT IDENTIFIER ::= { bypass 12 }

		-- 1.3.6.1.4.1.47477.10.21.12.3
		link12OBP OBJECT IDENTIFIER ::= { link12 3 }
		
		-- 1.3.6.1.4.1.47477.10.21.12.3.50		
		link12OBPTrap OBJECT IDENTIFIER ::= { link12OBP 50 }
				

		-- link13
		-- 1.3.6.1.4.1.47477.10.21.13
		link13 OBJECT IDENTIFIER ::= { bypass 13 }

		-- 1.3.6.1.4.1.47477.10.21.13.3
		link13OBP OBJECT IDENTIFIER ::= { link13 3 }
		
		-- 1.3.6.1.4.1.47477.10.21.13.3.50		
		link13OBPTrap OBJECT IDENTIFIER ::= { link13OBP 50 }
				

		-- link14
		-- 1.3.6.1.4.1.47477.10.21.14
		link14 OBJECT IDENTIFIER ::= { bypass 14 }

		-- 1.3.6.1.4.1.47477.10.21.14.3
		link14OBP OBJECT IDENTIFIER ::= { link14 3 }
		
		-- 1.3.6.1.4.1.47477.10.21.14.3.50		
		link14OBPTrap OBJECT IDENTIFIER ::= { link14OBP 50 }
				

		-- link15
		-- 1.3.6.1.4.1.47477.10.21.15
		link15 OBJECT IDENTIFIER ::= { bypass 15 }

		-- 1.3.6.1.4.1.47477.10.21.15.3
		link15OBP OBJECT IDENTIFIER ::= { link15 3 }
		
		-- 1.3.6.1.4.1.47477.10.21.15.3.50		
		link15OBPTrap OBJECT IDENTIFIER ::= { link15OBP 50 }
				

		-- link16
		-- 1.3.6.1.4.1.47477.10.21.16
		link16 OBJECT IDENTIFIER ::= { bypass 16 }

		-- 1.3.6.1.4.1.47477.10.21.16.3
		link16OBP OBJECT IDENTIFIER ::= { link16 3 }
		
		-- 1.3.6.1.4.1.47477.10.21.16.3.50		
		link16OBPTrap OBJECT IDENTIFIER ::= { link16OBP 50 }
				

		-- link17
		-- 1.3.6.1.4.1.47477.10.21.17
		link17 OBJECT IDENTIFIER ::= { bypass 17 }

		-- 1.3.6.1.4.1.47477.10.21.17.3
		link17OBP OBJECT IDENTIFIER ::= { link17 3 }
		
		-- 1.3.6.1.4.1.47477.10.21.17.3.50		
		link17OBPTrap OBJECT IDENTIFIER ::= { link17OBP 50 }
				

		-- link18
		-- 1.3.6.1.4.1.47477.10.21.18
		link18 OBJECT IDENTIFIER ::= { bypass 18 }

		-- 1.3.6.1.4.1.47477.10.21.18.3
		link18OBP OBJECT IDENTIFIER ::= { link18 3 }
		
		-- 1.3.6.1.4.1.47477.10.21.18.3.50		
		link18OBPTrap OBJECT IDENTIFIER ::= { link18OBP 50 }
				

		-- link19
		-- 1.3.6.1.4.1.47477.10.21.19
		link19 OBJECT IDENTIFIER ::= { bypass 19 }

		-- 1.3.6.1.4.1.47477.10.21.19.3
		link19OBP OBJECT IDENTIFIER ::= { link19 3 }
		
		-- 1.3.6.1.4.1.47477.10.21.19.3.50		
		link19OBPTrap OBJECT IDENTIFIER ::= { link19OBP 50 }
				

		-- link20
		-- 1.3.6.1.4.1.47477.10.21.20
		link20 OBJECT IDENTIFIER ::= { bypass 20 }

		-- 1.3.6.1.4.1.47477.10.21.20.3
		link20OBP OBJECT IDENTIFIER ::= { link20 3 }
		
		-- 1.3.6.1.4.1.47477.10.21.20.3.50		
		link20OBPTrap OBJECT IDENTIFIER ::= { link20OBP 50 }
						

		-- link21
		-- 1.3.6.1.4.1.47477.10.21.21
		link21 OBJECT IDENTIFIER ::= { bypass 21 }

		-- 1.3.6.1.4.1.47477.10.21.21.3
		link21OBP OBJECT IDENTIFIER ::= { link21 3 }
		
		-- 1.3.6.1.4.1.47477.10.21.21.3.50		
		link21OBPTrap OBJECT IDENTIFIER ::= { link21OBP 50 }
						

		-- link22
		-- 1.3.6.1.4.1.47477.10.21.22
		link22 OBJECT IDENTIFIER ::= { bypass 22 }

		-- 1.3.6.1.4.1.47477.10.21.22.3
		link22OBP OBJECT IDENTIFIER ::= { link22 3 }
		
		-- 1.3.6.1.4.1.47477.10.21.22.3.50		
		link22OBPTrap OBJECT IDENTIFIER ::= { link22OBP 50 }
						

		-- link23
		-- 1.3.6.1.4.1.47477.10.21.23
		link23 OBJECT IDENTIFIER ::= { bypass 23 }

		-- 1.3.6.1.4.1.47477.10.21.23.3
		link23OBP OBJECT IDENTIFIER ::= { link23 3 }
		
		-- 1.3.6.1.4.1.47477.10.21.23.3.50		
		link23OBPTrap OBJECT IDENTIFIER ::= { link23OBP 50 }
						

		-- link24
		-- 1.3.6.1.4.1.47477.10.21.24
		link24 OBJECT IDENTIFIER ::= { bypass 24 }

		-- 1.3.6.1.4.1.47477.10.21.24.3
		link24OBP OBJECT IDENTIFIER ::= { link24 3 }
		
		-- 1.3.6.1.4.1.47477.10.21.24.3.50		
		link24OBPTrap OBJECT IDENTIFIER ::= { link24OBP 50 }
								

		-- link25
		-- 1.3.6.1.4.1.47477.10.21.25
		link25 OBJECT IDENTIFIER ::= { bypass 25 }

		-- 1.3.6.1.4.1.47477.10.21.25.3
		link25OBP OBJECT IDENTIFIER ::= { link25 3 }
		
		-- 1.3.6.1.4.1.47477.10.21.25.3.50		
		link25OBPTrap OBJECT IDENTIFIER ::= { link25OBP 50 }
						

		-- link26
		-- 1.3.6.1.4.1.47477.10.21.26
		link26 OBJECT IDENTIFIER ::= { bypass 26 }

		-- 1.3.6.1.4.1.47477.10.21.26.3
		link26OBP OBJECT IDENTIFIER ::= { link26 3 }
		
		-- 1.3.6.1.4.1.47477.10.21.26.3.50		
		link26OBPTrap OBJECT IDENTIFIER ::= { link26OBP 50 }
						

		-- link27
		-- 1.3.6.1.4.1.47477.10.21.27
		link27 OBJECT IDENTIFIER ::= { bypass 27 }

		-- 1.3.6.1.4.1.47477.10.21.27.3
		link27OBP OBJECT IDENTIFIER ::= { link27 3 }
		
		-- 1.3.6.1.4.1.47477.10.21.27.3.50		
		link27OBPTrap OBJECT IDENTIFIER ::= { link27OBP 50 }	
						

		-- link28
		-- 1.3.6.1.4.1.47477.10.21.28
		link28 OBJECT IDENTIFIER ::= { bypass 28 }

		-- 1.3.6.1.4.1.47477.10.21.28.3
		link28OBP OBJECT IDENTIFIER ::= { link28 3 }
		
		-- 1.3.6.1.4.1.47477.10.21.28.3.50		
		link28OBPTrap OBJECT IDENTIFIER ::= { link28OBP 50 }	
						

		-- link29
		-- 1.3.6.1.4.1.47477.10.21.29
		link29 OBJECT IDENTIFIER ::= { bypass 29 }

		-- 1.3.6.1.4.1.47477.10.21.29.3
		link29OBP OBJECT IDENTIFIER ::= { link29 3 }
		
		-- 1.3.6.1.4.1.47477.10.21.29.3.50		
		link29OBPTrap OBJECT IDENTIFIER ::= { link29OBP 50 }
						

		-- link30
		-- 1.3.6.1.4.1.47477.10.21.30
		link30 OBJECT IDENTIFIER ::= { bypass 30 }

		-- 1.3.6.1.4.1.47477.10.21.30.3
		link30OBP OBJECT IDENTIFIER ::= { link30 3 }
		
		-- 1.3.6.1.4.1.47477.10.21.30.3.50		
		link30OBPTrap OBJECT IDENTIFIER ::= { link30OBP 50 }
						

		-- link31
		-- 1.3.6.1.4.1.47477.10.21.31
		link31 OBJECT IDENTIFIER ::= { bypass 31 }

		-- 1.3.6.1.4.1.47477.10.21.31.3
		link31OBP OBJECT IDENTIFIER ::= { link31 3 }
		
		-- 1.3.6.1.4.1.47477.10.21.31.3.50		
		link31OBPTrap OBJECT IDENTIFIER ::= { link31OBP 50 }	
						

		-- link32
		-- 1.3.6.1.4.1.47477.10.21.32
		link32 OBJECT IDENTIFIER ::= { bypass 32 }

		-- 1.3.6.1.4.1.47477.10.21.32.3
		link32OBP OBJECT IDENTIFIER ::= { link32 3 }
		
		-- 1.3.6.1.4.1.47477.10.21.32.3.50		
		link32OBPTrap OBJECT IDENTIFIER ::= { link32OBP 50 }		
		
		
		
	    -- 1.3.6.1.4.1.47477.10.21.60.1
		deviceType OBJECT-TYPE
			SYNTAX DisplayString
			MAX-ACCESS read-only
			STATUS current
			DESCRIPTION
				"Get the type of the device."
			::= { nmu 1 }

		
		-- 1.3.6.1.4.1.47477.10.21.60.2
		ipAddress OBJECT-TYPE
			SYNTAX IpAddress
			MAX-ACCESS read-write
			STATUS current
			DESCRIPTION
				"Get or set the IP address of the device."
			::= { nmu 2 }

		
		-- 1.3.6.1.4.1.47477.10.21.60.3
		subnetMask OBJECT-TYPE
			SYNTAX IpAddress
			MAX-ACCESS read-write
			STATUS current
			DESCRIPTION
				"Get or set the subnetMask of the device."
			::= { nmu 3 }

		
		-- 1.3.6.1.4.1.47477.10.21.60.4
		gateWay OBJECT-TYPE
			SYNTAX IpAddress
			MAX-ACCESS read-write
			STATUS current
			DESCRIPTION
				"Get or set the gateWay of the device."
			::= { nmu 4 }

		
		-- 1.3.6.1.4.1.47477.10.21.60.5
		macAddress OBJECT-TYPE
			SYNTAX DisplayString
			MAX-ACCESS read-only
			STATUS current
			DESCRIPTION
				"Get the macAddress of the device."
			::= { nmu 5 }
  
		-- 1.3.6.1.4.1.47477.10.21.60.6
		tcpPort OBJECT-TYPE
			SYNTAX Integer32
			MAX-ACCESS read-write
			STATUS current
			DESCRIPTION
				"Get or set the tcpPort of the device."
			::= { nmu 6 }

		-- 1.3.6.1.4.1.47477.10.21.60.7
		startDelay OBJECT-TYPE
			SYNTAX Integer32
			MAX-ACCESS read-write
			STATUS current
			DESCRIPTION
				"Get or set the startDelay of the device."
			::= { nmu 7 }
			
		-- 1.3.6.1.4.1.47477.10.21.60.8
		keyLock OBJECT-TYPE
			SYNTAX INTEGER
				{
				lock(0),
				unlock(1)
				}
			MAX-ACCESS read-write
			STATUS current
			DESCRIPTION
				"Get or set the keyboard lock status of the device."
			::= { nmu 8 }

		
		-- 1.3.6.1.4.1.47477.10.21.60.9
		buzzerSet OBJECT-TYPE
			SYNTAX INTEGER
				{
				off(0),
				on(1)
				}
			MAX-ACCESS read-write
			STATUS current
			DESCRIPTION
				"Get or set the buzzer status of the device."
			::= { nmu 9 }


		-- 1.3.6.1.4.1.47477.10.21.60.10
		deviceAddress OBJECT-TYPE
			SYNTAX Integer32
			MAX-ACCESS read-write
			STATUS current
			DESCRIPTION
				"Get or set the deviceAddress of the device."
			::= { nmu 10 }

		
		-- 1.3.6.1.4.1.47477.10.21.60.11
		power1State OBJECT-TYPE
			SYNTAX INTEGER
				{
				off(0),
				on(1)
				}
			MAX-ACCESS read-only
			STATUS current
			DESCRIPTION
				"Get the power1 status of the device."
			::= { nmu 11 }

		
		-- 1.3.6.1.4.1.47477.10.21.60.12
		power2State OBJECT-TYPE
			SYNTAX INTEGER
				{
				off(0),
				on(1)
				}
			MAX-ACCESS read-only
			STATUS current
			DESCRIPTION
				"Get the power2 status of the device."
			::= { nmu 12 }

		
		-- 1.3.6.1.4.1.47477.10.21.60.13
		softwareVersion OBJECT-TYPE
			SYNTAX DisplayString
			MAX-ACCESS read-only
			STATUS current
			DESCRIPTION
				"Get the softwareVersion of the device."
			::= { nmu 13 }

		
		-- 1.3.6.1.4.1.47477.10.21.60.14
		hardwareVersion OBJECT-TYPE
			SYNTAX DisplayString
			MAX-ACCESS read-only
			STATUS current
			DESCRIPTION
				"Get the hardwareVersion of the device."
			::= { nmu 14 }

		
		-- 1.3.6.1.4.1.47477.10.21.60.15
		serialNumber OBJECT-TYPE
			SYNTAX DisplayString
			MAX-ACCESS read-only
			STATUS current
			DESCRIPTION
				"Get the serialNumber of the device."
			::= { nmu 15 }

		
		-- 1.3.6.1.4.1.47477.10.21.60.16
		manufacturingdate OBJECT-TYPE
			SYNTAX DisplayString
			MAX-ACCESS read-only
			STATUS current
			DESCRIPTION
				"Get the manufacturingdate of the device."
			::= { nmu 16 }



-- 1.3.6.1.4.1.47477.10.21.60.50.1
	systemStartup 	OBJECT-TYPE
		SYNTAX DisplayString
		MAX-ACCESS read-only
		STATUS current
		DESCRIPTION
        "System Startup."
    ::= { nmuTrap 1 }
	
-- 1.3.6.1.4.1.47477.10.21.60.50.2
	cardStatusChanged 	OBJECT-TYPE
		SYNTAX DisplayString
		MAX-ACCESS read-only
		STATUS current
		DESCRIPTION
        "Card Status Alarm."
    ::= { nmuTrap 2 }	
	
--  1.3.6.1.4.1.47477.10.21.1.3.1
		-- 1.3.6.1.4.1.47477.10.21.1.3.1
		link1_State OBJECT-TYPE
			SYNTAX INTEGER
				{
				off(0),
				on(1)
				}
			MAX-ACCESS read-only
			STATUS current
			DESCRIPTION
				"get the information about whether link1 is working."
			::= { link1OBP 1 }

		
--  1.3.6.1.4.1.47477.10.21.1.3.2
		-- 1.3.6.1.4.1.47477.10.21.1.3.2
		link1_DeviceType OBJECT-TYPE
			SYNTAX DisplayString
			MAX-ACCESS read-only
			STATUS current
			DESCRIPTION
				"get the type of card in link1."
			::= { link1OBP 2 }

			
--  1.3.6.1.4.1.47477.10.21.1.3.3
		-- 1.3.6.1.4.1.47477.10.21.1.3.3
		link1_WorkMode OBJECT-TYPE
			SYNTAX INTEGER
				{
				manualMode(0),
				autoMode(1)
				}
			MAX-ACCESS read-write
			STATUS current
			DESCRIPTION
				"get or set link1's work mode."
			::= { link1OBP 3 }

		
--  1.3.6.1.4.1.47477.10.21.1.3.4
		-- 1.3.6.1.4.1.47477.10.21.1.3.4
		link1_Channel OBJECT-TYPE
			SYNTAX INTEGER
				{
				bypass(0),
				primary(1)
				}
			MAX-ACCESS read-write
			STATUS current
			DESCRIPTION
				"get or set the channel in which link1 works."
			::= { link1OBP 4 }


--  1.3.6.1.4.1.47477.10.21.1.3.5
		-- 1.3.6.1.4.1.47477.10.21.1.3.5
		link1_R1Power OBJECT-TYPE
			SYNTAX DisplayString
			MAX-ACCESS read-only
			STATUS current
			DESCRIPTION
				"get the power of R1 in link1."
			::= { link1OBP 5 }

		
--  1.3.6.1.4.1.47477.10.21.1.3.6
		-- 1.3.6.1.4.1.47477.10.21.1.3.6
		link1_R2Power OBJECT-TYPE
			SYNTAX DisplayString
			MAX-ACCESS read-only
			STATUS current
			DESCRIPTION
				"get the power of R2 in link1."
			::= { link1OBP 6 }
			
--  1.3.6.1.4.1.47477.10.21.1.3.35
		-- 1.3.6.1.4.1.47477.10.21.1.3.35
		link1_R3Power OBJECT-TYPE
			SYNTAX DisplayString
			MAX-ACCESS read-only
			STATUS current
			DESCRIPTION
				"get the power of R3 in link1."
			::= { link1OBP 35 }
			
--  1.3.6.1.4.1.47477.10.21.1.3.36
		-- 1.3.6.1.4.1.47477.10.21.1.3.36
		link1_R4Power OBJECT-TYPE
			SYNTAX DisplayString
			MAX-ACCESS read-only
			STATUS current
			DESCRIPTION
				"get the power of R4 in link1."
			::= { link1OBP 36 }		
		
--  1.3.6.1.4.1.47477.10.21.1.3.7
		-- 1.3.6.1.4.1.47477.10.21.1.3.7
		link1_R1Wave OBJECT-TYPE
			SYNTAX INTEGER
				{
				w1310nm(0),
				w1550nm(1),
				na(2)
				}
			MAX-ACCESS read-write
			STATUS current
			DESCRIPTION
				"get or set the wave length of R1 in link1."
			::= { link1OBP 7 }

		
--  1.3.6.1.4.1.47477.10.21.1.3.8
		-- 1.3.6.1.4.1.47477.10.21.1.3.8
		link1_R2Wave OBJECT-TYPE
			SYNTAX INTEGER
				{
				w1310nm(0),
				w1550nm(1),
				na(2)
				}
			MAX-ACCESS read-write
			STATUS current
			DESCRIPTION
				"get or set the wave length of R2 in link1."
			::= { link1OBP 8 }


--  1.3.6.1.4.1.47477.10.21.1.3.27
		-- 1.3.6.1.4.1.47477.10.21.1.3.27
		link1_R3Wave OBJECT-TYPE
			SYNTAX INTEGER
				{
				w1310nm(0),
				w1550nm(1),
				na(2)
				}
			MAX-ACCESS read-write
			STATUS current
			DESCRIPTION
				"get or set the wave length of R3 in link1."
			::= { link1OBP 27 }

		
--  1.3.6.1.4.1.47477.10.21.1.3.28
		-- 1.3.6.1.4.1.47477.10.21.1.3.28
		link1_R4Wave OBJECT-TYPE
			SYNTAX INTEGER
				{
				w1310nm(0),
				w1550nm(1),
				na(2)
				}
			MAX-ACCESS read-write
			STATUS current
			DESCRIPTION
				"get or set the wave length of R4 in link1."
			::= { link1OBP 28 }
			
--  1.3.6.1.4.1.47477.10.21.1.3.9
		-- 1.3.6.1.4.1.47477.10.21.1.3.9
		link1_R1AlarmPower OBJECT-TYPE
			SYNTAX DisplayString
			MAX-ACCESS read-write
			STATUS current
			DESCRIPTION
				"get or set the power alarm threshold of R1 in link1."
			::= { link1OBP 9 }

		
--  1.3.6.1.4.1.47477.10.21.1.3.10
		-- 1.3.6.1.4.1.47477.10.21.1.3.10
		link1_R2AlarmPower OBJECT-TYPE
			SYNTAX DisplayString
			MAX-ACCESS read-write
			STATUS current
			DESCRIPTION
				"get or set the power alarm threshold of R2 in link1."
			::= { link1OBP 10 }


--  1.3.6.1.4.1.47477.10.21.1.3.29
		-- 1.3.6.1.4.1.47477.10.21.1.3.29
		link1_R3AlarmPower OBJECT-TYPE
			SYNTAX DisplayString
			MAX-ACCESS read-write
			STATUS current
			DESCRIPTION
				"get or set the power alarm threshold of R3 in link1."
			::= { link1OBP 29 }

		
--  1.3.6.1.4.1.47477.10.21.1.3.30
		-- 1.3.6.1.4.1.47477.10.21.1.3.30
		link1_R4AlarmPower OBJECT-TYPE
			SYNTAX DisplayString
			MAX-ACCESS read-write
			STATUS current
			DESCRIPTION
				"get or set the power alarm threshold of R4 in link1."
			::= { link1OBP 30 }

-- OBP4
--  1.3.6.1.4.1.47477.10.21.1.3.37
		-- 1.3.6.1.4.1.47477.10.21.1.3.37
		link1_1R1Power OBJECT-TYPE
			SYNTAX DisplayString
			MAX-ACCESS read-only
			STATUS current
			DESCRIPTION
				"get the power of 1R1 in link1."
			::= { link1OBP 37 }
			
--  1.3.6.1.4.1.47477.10.21.1.3.38
		-- 1.3.6.1.4.1.47477.10.21.1.3.38
		link1_1R2Power OBJECT-TYPE
			SYNTAX DisplayString
			MAX-ACCESS read-only
			STATUS current
			DESCRIPTION
				"get the power of 1R2 in link1."
			::= { link1OBP 38 }

--  1.3.6.1.4.1.47477.10.21.1.3.39
		-- 1.3.6.1.4.1.47477.10.21.1.3.39
		link1_1R3Power OBJECT-TYPE
			SYNTAX DisplayString
			MAX-ACCESS read-only
			STATUS current
			DESCRIPTION
				"get the power of 1R3 in link1."
			::= { link1OBP 39 }
			
--  1.3.6.1.4.1.47477.10.21.1.3.40
		-- 1.3.6.1.4.1.47477.10.21.1.3.40
		link1_1R4Power OBJECT-TYPE
			SYNTAX DisplayString
			MAX-ACCESS read-only
			STATUS current
			DESCRIPTION
				"get the power of 1R4 in link1."
			::= { link1OBP 40 }

--  1.3.6.1.4.1.47477.10.21.1.3.41
		-- 1.3.6.1.4.1.47477.10.21.1.3.41
		link1_2R1Power OBJECT-TYPE
			SYNTAX DisplayString
			MAX-ACCESS read-only
			STATUS current
			DESCRIPTION
				"get the power of 2R1 in link1."
			::= { link1OBP 41 }
			
--  1.3.6.1.4.1.47477.10.21.1.3.42
		-- 1.3.6.1.4.1.47477.10.21.1.3.42
		link1_2R2Power OBJECT-TYPE
			SYNTAX DisplayString
			MAX-ACCESS read-only
			STATUS current
			DESCRIPTION
				"get the power of 2R2 in link1."
			::= { link1OBP 42 }

--  1.3.6.1.4.1.47477.10.21.1.3.41
		-- 1.3.6.1.4.1.47477.10.21.1.3.43
		link1_2R3Power OBJECT-TYPE
			SYNTAX DisplayString
			MAX-ACCESS read-only
			STATUS current
			DESCRIPTION
				"get the power of 2R3 in link1."
			::= { link1OBP 43 }
			
--  1.3.6.1.4.1.47477.10.21.1.3.42
		-- 1.3.6.1.4.1.47477.10.21.1.3.44
		link1_2R4Power OBJECT-TYPE
			SYNTAX DisplayString
			MAX-ACCESS read-only
			STATUS current
			DESCRIPTION
				"get the power of 2R4 in link1."
			::= { link1OBP 44 }
			
--  1.3.6.1.4.1.47477.10.21.1.3.49
		-- 1.3.6.1.4.1.47477.10.21.1.3.49
		link1_1R1Wave OBJECT-TYPE
			SYNTAX INTEGER
				{
				w850nm(0),
				na(2)
				}
			MAX-ACCESS read-only
			STATUS current
			DESCRIPTION
				"get the wave length of 1R1 in link1."
			::= { link1OBP 49 }
		
--  1.3.6.1.4.1.47477.10.21.1.3.60
		-- 1.3.6.1.4.1.47477.10.21.1.3.60
		link1_1R2Wave OBJECT-TYPE
			SYNTAX INTEGER
				{
				w850nm(0),
				na(2)
				}
			MAX-ACCESS read-only
			STATUS current
			DESCRIPTION
				"get the wave length of 1R2 in link1."
			::= { link1OBP 60 }

--  1.3.6.1.4.1.47477.10.21.1.3.61
		-- 1.3.6.1.4.1.47477.10.21.1.3.61
		link1_1R3Wave OBJECT-TYPE
			SYNTAX INTEGER
				{
				w850nm(0),
				na(2)
				}
			MAX-ACCESS read-only
			STATUS current
			DESCRIPTION
				"get the wave length of 1R3 in link1."
			::= { link1OBP 61 }

		
--  1.3.6.1.4.1.47477.10.21.1.3.62
		-- 1.3.6.1.4.1.47477.10.21.1.3.62
		link1_1R4Wave OBJECT-TYPE
			SYNTAX INTEGER
				{
				w850nm(0),
				na(2)
				}
			MAX-ACCESS read-only
			STATUS current
			DESCRIPTION
				"get the wave length of 1R4 in link1."
			::= { link1OBP 62 }
	
--  1.3.6.1.4.1.47477.10.21.1.3.63
		-- 1.3.6.1.4.1.47477.10.21.1.3.63
		link1_2R1Wave OBJECT-TYPE
			SYNTAX INTEGER
				{
				w850nm(0),
				na(2)
				}
			MAX-ACCESS read-only
			STATUS current
			DESCRIPTION
				"get the wave length of 2R1 in link1."
			::= { link1OBP 63 }

		
--  1.3.6.1.4.1.47477.10.21.1.3.64
		-- 1.3.6.1.4.1.47477.10.21.1.3.64
		link1_2R2Wave OBJECT-TYPE
			SYNTAX INTEGER
				{
				w850nm(0),
				na(2)
				}
			MAX-ACCESS read-only
			STATUS current
			DESCRIPTION
				"get the wave length of 2R2 in link1."
			::= { link1OBP 64 }	
	
--  1.3.6.1.4.1.47477.10.21.1.3.65
		-- 1.3.6.1.4.1.47477.10.21.1.3.65
		link1_2R3Wave OBJECT-TYPE
			SYNTAX INTEGER
				{
				w850nm(0),
				na(2)
				}
			MAX-ACCESS read-only
			STATUS current
			DESCRIPTION
				"get the wave length of 2R3 in link1."
			::= { link1OBP 65 }

		
--  1.3.6.1.4.1.47477.10.21.1.3.66
		-- 1.3.6.1.4.1.47477.10.21.1.3.66
		link1_2R4Wave OBJECT-TYPE
			SYNTAX INTEGER
				{
				w850nm(0),
				na(2)
				}
			MAX-ACCESS read-only
			STATUS current
			DESCRIPTION
				"get the wave length of 2R4 in link1."
			::= { link1OBP 66 }	
			
--  1.3.6.1.4.1.47477.10.21.1.3.31
		-- 1.3.6.1.4.1.47477.10.21.1.3.31
		link1_1R1AlarmPower OBJECT-TYPE
			SYNTAX DisplayString
			MAX-ACCESS read-write
			STATUS current
			DESCRIPTION
				"get or set the power alarm threshold of 1R1 in link1."
			::= { link1OBP 31 }
			
--  1.3.6.1.4.1.47477.10.21.1.3.32
		-- 1.3.6.1.4.1.47477.10.21.1.3.32
		link1_1R2AlarmPower OBJECT-TYPE
			SYNTAX DisplayString
			MAX-ACCESS read-write
			STATUS current
			DESCRIPTION
				"get or set the power alarm threshold of 1R2 in link1."
			::= { link1OBP 32 }

--  1.3.6.1.4.1.47477.10.21.1.3.33
		-- 1.3.6.1.4.1.47477.10.21.1.3.33
		link1_1R3AlarmPower OBJECT-TYPE
			SYNTAX DisplayString
			MAX-ACCESS read-write
			STATUS current
			DESCRIPTION
				"get or set the power alarm threshold of 1R3 in link1."
			::= { link1OBP 33 }
			
--  1.3.6.1.4.1.47477.10.21.1.3.34
		-- 1.3.6.1.4.1.47477.10.21.1.3.34
		link1_1R4AlarmPower OBJECT-TYPE
			SYNTAX DisplayString
			MAX-ACCESS read-write
			STATUS current
			DESCRIPTION
				"get or set the power alarm threshold of 1R4 in link1."
			::= { link1OBP 34 }

--  1.3.6.1.4.1.47477.10.21.1.3.45
		-- 1.3.6.1.4.1.47477.10.21.1.3.45
		link1_2R1AlarmPower OBJECT-TYPE
			SYNTAX DisplayString
			MAX-ACCESS read-write
			STATUS current
			DESCRIPTION
				"get or set the power alarm threshold of 2R1 in link1."
			::= { link1OBP 45 }
			
--  1.3.6.1.4.1.47477.10.21.1.3.46
		-- 1.3.6.1.4.1.47477.10.21.1.3.46
		link1_2R2AlarmPower OBJECT-TYPE
			SYNTAX DisplayString
			MAX-ACCESS read-write
			STATUS current
			DESCRIPTION
				"get or set the power alarm threshold of 2R2 in link1."
			::= { link1OBP 46 }

--  1.3.6.1.4.1.47477.10.21.1.3.47
		-- 1.3.6.1.4.1.47477.10.21.1.3.47
		link1_2R3AlarmPower OBJECT-TYPE
			SYNTAX DisplayString
			MAX-ACCESS read-write
			STATUS current
			DESCRIPTION
				"get or set the power alarm threshold of 2R3 in link1."
			::= { link1OBP 47 }
			
--  1.3.6.1.4.1.47477.10.21.1.3.48
		-- 1.3.6.1.4.1.47477.10.21.1.3.48
		link1_2R4AlarmPower OBJECT-TYPE
			SYNTAX DisplayString
			MAX-ACCESS read-write
			STATUS current
			DESCRIPTION
				"get or set the power alarm threshold of 2R4 in link1."
			::= { link1OBP 48 }
			
--  1.3.6.1.4.1.47477.10.21.1.3.11
		-- 1.3.6.1.4.1.47477.10.21.1.3.11
		link1_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link1OBP 11 }
			
--  1.3.6.1.4.1.47477.10.21.1.3.67
		-- 1.3.6.1.4.1.47477.10.21.1.3.67
		link1_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link1OBP 67 }
			
--  1.3.6.1.4.1.47477.10.21.1.3.68
		-- 1.3.6.1.4.1.47477.10.21.1.3.68
		link1_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link1OBP 68 }
			
--  1.3.6.1.4.1.47477.10.21.1.3.12
		-- 1.3.6.1.4.1.47477.10.21.1.3.12
		link1_ReturnDelay OBJECT-TYPE
			--SYNTAX Integer32
			SYNTAX Integer32
			MAX-ACCESS read-write
			STATUS current
			DESCRIPTION
				"get or set how long link1 takes to return to automatic mode."
			::= { link1OBP 12 }
			
--  1.3.6.1.4.1.47477.10.21.1.3.13
		-- 1.3.6.1.4.1.47477.10.21.1.3.13
		link1_BackMode OBJECT-TYPE
			SYNTAX INTEGER
				{
				autoNoBack(0),
				autoBack(1)
				}
			MAX-ACCESS read-write
			STATUS current
			DESCRIPTION
				"get or set the back mode of link1."
			::= { link1OBP 13 }

		
--  1.3.6.1.4.1.47477.10.21.1.3.14
		-- 1.3.6.1.4.1.47477.10.21.1.3.14
		link1_BackDelay OBJECT-TYPE
			SYNTAX Integer32
			MAX-ACCESS read-write
			STATUS current
			DESCRIPTION
				"get or set the back delay."
			::= { link1OBP 14 }

--  1.3.6.1.4.1.47477.10.21.1.3.15
		-- 1.3.6.1.4.1.47477.10.21.1.3.15
		link1_ActiveHeartSwitch OBJECT-TYPE
			SYNTAX INTEGER
				{
				off(0),
				on(1)
				}
			MAX-ACCESS read-write
			STATUS current
			DESCRIPTION
				"get or set the switch status of active heartbeat."
			::= { link1OBP 15 }

		
--  1.3.6.1.4.1.47477.10.21.1.3.16
		-- 1.3.6.1.4.1.47477.10.21.1.3.16
		link1_ActiveSendInterval OBJECT-TYPE
			SYNTAX Integer32
			MAX-ACCESS read-write
			STATUS current
			DESCRIPTION
				"get or set the send interval of active heartbeat."
			::= { link1OBP 16 }		

--  1.3.6.1.4.1.47477.10.21.1.3.17
		-- 1.3.6.1.4.1.47477.10.21.1.3.17
		link1_ActiveTimeOut OBJECT-TYPE
			SYNTAX Integer32
			MAX-ACCESS read-write
			STATUS current
			DESCRIPTION
				"get or set how long the active heartbeat send timeout."
			::= { link1OBP 17 }

--  1.3.6.1.4.1.47477.10.21.1.3.18
		-- 1.3.6.1.4.1.47477.10.21.1.3.18
		link1_ActiveLossBypass OBJECT-TYPE
			SYNTAX Integer32
			MAX-ACCESS read-write
			STATUS current
			DESCRIPTION
				"get or set the bypass for active heartbeat packet loss."
			::= { link1OBP 18 }

--  1.3.6.1.4.1.47477.10.21.1.3.19
		-- 1.3.6.1.4.1.47477.10.21.1.3.19
		link1_PingIpAddress OBJECT-TYPE
			SYNTAX IpAddress
			MAX-ACCESS read-write
			STATUS current
			DESCRIPTION
				"get or set the ping ip address of link1."
			::= { link1OBP 19 }

--  1.3.6.1.4.1.47477.10.21.1.3.20
		-- 1.3.6.1.4.1.47477.10.21.1.3.20
		link1_PassiveHeartSwitch OBJECT-TYPE
			SYNTAX INTEGER
				{
				off(0),
				on(1)
				}
			MAX-ACCESS read-write
			STATUS current
			DESCRIPTION
				"get or set the switch status of passive heartbeat."
			::= { link1OBP 20 }
	

--  1.3.6.1.4.1.47477.10.21.1.3.21
		-- 1.3.6.1.4.1.47477.10.21.1.3.21
		link1_PassiveTimeOut OBJECT-TYPE
			SYNTAX Integer32
			MAX-ACCESS read-write
			STATUS current
			DESCRIPTION
				"get or set how long the passive heartbeat send timeout."
			::= { link1OBP 21 }

--  1.3.6.1.4.1.47477.10.21.1.3.22
		-- 1.3.6.1.4.1.47477.10.21.1.3.22
		link1_PassiveLossBypass OBJECT-TYPE
			SYNTAX Integer32
			MAX-ACCESS read-write
			STATUS current
			DESCRIPTION
				"get or set the bypass for passive heartbeat packet loss."
			::= { link1OBP 22 }

--  1.3.6.1.4.1.47477.10.21.1.3.23
		-- 1.3.6.1.4.1.47477.10.21.1.3.23
		link1_SwitchProtect OBJECT-TYPE
			SYNTAX INTEGER
				{
				off(0),
				on(1)
				}
			MAX-ACCESS read-write
			STATUS current
			DESCRIPTION
				"get or set the switch protection status of link1."
			::= { link1OBP 23 }
			
--  1.3.6.1.4.1.47477.10.21.1.3.24
		-- 1.3.6.1.4.1.47477.10.21.1.3.24
		link1_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link1OBP 24 }		

--  1.3.6.1.4.1.47477.10.21.1.3.25
		-- 1.3.6.1.4.1.47477.10.21.1.3.25
		link1_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link1OBP 25 }	

--  1.3.6.1.4.1.47477.10.21.1.3.26
		-- 1.3.6.1.4.1.47477.10.21.1.3.26
		link1_PowerAlarmStatus OBJECT-TYPE
			SYNTAX INTEGER
				{
				off(0),
				alarm(1),
				normal(2),
				na(3)
				}
			MAX-ACCESS read-only
			STATUS current
			DESCRIPTION
				"get whether a power alarm is generated."
			::= { link1OBP 26 }	


-- 1.3.6.1.4.1.47477.10.21.1.3.50.1
	link1_WorkModeChange 	OBJECT-TYPE    
    SYNTAX INTEGER	{
				manualMode(0),
				autoMode(1)
		}
	MAX-ACCESS read-only
	STATUS current
    DESCRIPTION
        "The Link mode Changed."
    ::= {link1OBPTrap 1}

-- 1.3.6.1.4.1.47477.10.21.1.3.50.2
	link1_StateChange 	OBJECT-TYPE    
    SYNTAX INTEGER	{
				bypass(0),
				primary(1)
		}
	MAX-ACCESS read-only
	STATUS current
    DESCRIPTION
        "The Link State(Channel) Changed."
    ::= {link1OBPTrap 2}

-- 1.3.6.1.4.1.47477.10.21.1.3.50.3
	link1_R1WaveSet 	OBJECT-TYPE    
    SYNTAX INTEGER	{
				w1310nm(0),
				w1550nm(1)
		}
	MAX-ACCESS read-only
	STATUS current
    DESCRIPTION
        "Set The Link1 R1 Wave."
    ::= {link1OBPTrap 3}

-- 1.3.6.1.4.1.47477.10.21.1.3.50.4
	link1_R2WaveSet 	OBJECT-TYPE    
    SYNTAX INTEGER	{
				w1310nm(0),
				w1550nm(1)
		}
	MAX-ACCESS read-only
	STATUS current
    DESCRIPTION
        "Set The Link1 R2 Wave."
    ::= {link1OBPTrap 4}			

-- 1.3.6.1.4.1.47477.10.21.1.3.50.5
	link1_R3WaveSet 	OBJECT-TYPE    
    SYNTAX INTEGER	{
				w1310nm(0),
				w1550nm(1)
		}
	MAX-ACCESS read-only
	STATUS current
    DESCRIPTION
        "Set The Link1 R3 Wave."
    ::= {link1OBPTrap 5}

-- 1.3.6.1.4.1.47477.10.21.1.3.50.6
	link1_R4WaveSet 	OBJECT-TYPE    
    SYNTAX INTEGER	{
				w1310nm(0),
				w1550nm(1)
		}
	MAX-ACCESS read-only
	STATUS current
    DESCRIPTION
        "Set The Link1 R4 Wave."
    ::= {link1OBPTrap 6}	
	
-- 1.3.6.1.4.1.47477.10.21.1.3.50.7
	link1_R1AlarmSet 	OBJECT-TYPE    
    SYNTAX DisplayString
	MAX-ACCESS read-only
	STATUS current
    DESCRIPTION
        "Set The Link1 R1 Alarm Threshold."
    ::= {link1OBPTrap 7}

-- 1.3.6.1.4.1.47477.10.21.1.3.50.8
	link1_R2AlarmSet 	OBJECT-TYPE    
    SYNTAX DisplayString
	MAX-ACCESS read-only
	STATUS current
    DESCRIPTION
        "Set The Link1 R2 Alarm Threshold."
    ::= {link1OBPTrap 8}
	
-- 1.3.6.1.4.1.47477.10.21.1.3.50.9
	link1_R3AlarmSet 	OBJECT-TYPE    
    SYNTAX DisplayString
	MAX-ACCESS read-only
	STATUS current
    DESCRIPTION
        "Set The Link1 R3 Alarm Threshold."
    ::= {link1OBPTrap 9}

-- 1.3.6.1.4.1.47477.10.21.1.3.50.10
	link1_R4AlarmSet 	OBJECT-TYPE    
    SYNTAX DisplayString
	MAX-ACCESS read-only
	STATUS current
    DESCRIPTION
        "Set The Link1 R4 Alarm Threshold."
    ::= {link1OBPTrap 10}	
	
	
-- 1.3.6.1.4.1.47477.10.21.1.3.50.11
	link1_1R1AlarmSet 	OBJECT-TYPE    
    SYNTAX DisplayString
	MAX-ACCESS read-only
	STATUS current
    DESCRIPTION
        "Set The Link1 1R1 Alarm Threshold."
    ::= {link1OBPTrap 11}

-- 1.3.6.1.4.1.47477.10.21.1.3.50.12
	link1_2R1AlarmSet 	OBJECT-TYPE    
    SYNTAX DisplayString
	MAX-ACCESS read-only
	STATUS current
    DESCRIPTION
        "Set The Link1 2R1 Alarm Threshold."
    ::= {link1OBPTrap 12}
	
-- 1.3.6.1.4.1.47477.10.21.1.3.50.13
	link1_1R2AlarmSet 	OBJECT-TYPE    
    SYNTAX DisplayString
	MAX-ACCESS read-only
	STATUS current
    DESCRIPTION
        "Set The Link1 1R2 Alarm Threshold."
    ::= {link1OBPTrap 13}

-- 1.3.6.1.4.1.47477.10.21.1.3.50.14
	link1_2R2AlarmSet 	OBJECT-TYPE    
    SYNTAX DisplayString
	MAX-ACCESS read-only
	STATUS current
    DESCRIPTION
        "Set The Link1 2R2 Alarm Threshold."
    ::= {link1OBPTrap 14}
	
-- 1.3.6.1.4.1.47477.10.21.1.3.50.15
	link1_1R3AlarmSet 	OBJECT-TYPE    
    SYNTAX DisplayString
	MAX-ACCESS read-only
	STATUS current
    DESCRIPTION
        "Set The Link1 1R3 Alarm Threshold."
    ::= {link1OBPTrap 15}

-- 1.3.6.1.4.1.47477.10.21.1.3.50.16
	link1_2R3AlarmSet 	OBJECT-TYPE    
    SYNTAX DisplayString
	MAX-ACCESS read-only
	STATUS current
    DESCRIPTION
        "Set The Link1 2R3 Alarm Threshold."
    ::= {link1OBPTrap 16}
	
-- 1.3.6.1.4.1.47477.10.21.1.3.50.17
	link1_1R4AlarmSet 	OBJECT-TYPE    
    SYNTAX DisplayString
	MAX-ACCESS read-only
	STATUS current
    DESCRIPTION
        "Set The Link1 1R4 Alarm Threshold."
    ::= {link1OBPTrap 17}

-- 1.3.6.1.4.1.47477.10.21.1.3.50.18
	link1_2R4AlarmSet 	OBJECT-TYPE    
    SYNTAX DisplayString
	MAX-ACCESS read-only
	STATUS current
    DESCRIPTION
        "Set The Link1 2R4 Alarm Threshold."
    ::= {link1OBPTrap 18}
	
-- 1.3.6.1.4.1.47477.10.21.1.3.50.19
	link1_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The Link1 PowerAlarmBypass2 Changed."
    ::= {link1OBPTrap 19}
	
-- 1.3.6.1.4.1.47477.10.21.1.3.50.20
	link1_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The Link1 PowerAlarmBypass4 Changed."
    ::= {link1OBPTrap 20}	
	
-- 1.3.6.1.4.1.47477.10.21.1.3.50.21
	link1_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The Link1 PowerAlarmBypass8 Changed."
    ::= {link1OBPTrap 21}
	
-- 1.3.6.1.4.1.47477.10.21.1.3.50.22
	link1_powerAlarmR1 	OBJECT-TYPE    
    SYNTAX DisplayString
	MAX-ACCESS read-only
	STATUS current
    DESCRIPTION
        "Set The Link1 R1 Power Status Alarm."
    ::= {link1OBPTrap 22}
	
-- 1.3.6.1.4.1.47477.10.21.1.3.50.23
	link1_powerAlarmR2 	OBJECT-TYPE    
    SYNTAX DisplayString
	MAX-ACCESS read-only
	STATUS current
    DESCRIPTION
        "Set The Link1 R2 Power Status Alarm."
    ::= {link1OBPTrap 23}
	
-- 1.3.6.1.4.1.47477.10.21.1.3.50.24
	link1_powerAlarmR3 	OBJECT-TYPE    
    SYNTAX DisplayString
	MAX-ACCESS read-only
	STATUS current
    DESCRIPTION
        "Set The Link1 R3 Power Status Alarm."
    ::= {link1OBPTrap 24}
	
-- 1.3.6.1.4.1.47477.10.21.1.3.50.25
	link1_powerAlarmR4 	OBJECT-TYPE    
    SYNTAX DisplayString
	MAX-ACCESS read-only
	STATUS current
    DESCRIPTION
        "Set The Link1 R4 Power Status Alarm."
    ::= {link1OBPTrap 25}
	
	
-- 1.3.6.1.4.1.47477.10.21.1.3.50.26
	link1_powerAlarm1R1 	OBJECT-TYPE    
    SYNTAX DisplayString
	MAX-ACCESS read-only
	STATUS current
    DESCRIPTION
        "Set The Link1 1R1 Power Status Alarm."
    ::= {link1OBPTrap 26}
	
-- 1.3.6.1.4.1.47477.10.21.1.3.50.27
	link1_powerAlarm2R1 	OBJECT-TYPE    
    SYNTAX DisplayString
	MAX-ACCESS read-only
	STATUS current
    DESCRIPTION
        "Set The Link1 2R1 Power Status Alarm."
    ::= {link1OBPTrap 27}
	
-- 1.3.6.1.4.1.47477.10.21.1.3.50.28
	link1_powerAlarm1R2 	OBJECT-TYPE    
    SYNTAX DisplayString
	MAX-ACCESS read-only
	STATUS current
    DESCRIPTION
        "Set The Link1 1R2 Power Status Alarm."
    ::= {link1OBPTrap 28}
	
-- 1.3.6.1.4.1.47477.10.21.1.3.50.29
	link1_powerAlarm2R2 	OBJECT-TYPE    
    SYNTAX DisplayString
	MAX-ACCESS read-only
	STATUS current
    DESCRIPTION
        "Set The Link1 2R2 Power Status Alarm."
    ::= {link1OBPTrap 29}
	
-- 1.3.6.1.4.1.47477.10.21.1.3.50.30
	link1_powerAlarm1R3 	OBJECT-TYPE    
    SYNTAX DisplayString
	MAX-ACCESS read-only
	STATUS current
    DESCRIPTION
        "Set The Link1 1R3 Power Status Alarm."
    ::= {link1OBPTrap 30}
	
-- 1.3.6.1.4.1.47477.10.21.1.3.50.31
	link1_powerAlarm2R3 	OBJECT-TYPE    
    SYNTAX DisplayString
	MAX-ACCESS read-only
	STATUS current
    DESCRIPTION
        "Set The Link1 2R1 Power Status Alarm."
    ::= {link1OBPTrap 31}
	
-- 1.3.6.1.4.1.47477.10.21.1.3.50.32
	link1_powerAlarm1R4 	OBJECT-TYPE    
    SYNTAX DisplayString
	MAX-ACCESS read-only
	STATUS current
    DESCRIPTION
        "Set The Link1 1R4 Power Status Alarm."
    ::= {link1OBPTrap 32}
	
-- 1.3.6.1.4.1.47477.10.21.1.3.50.33
	link1_powerAlarm2R4 	OBJECT-TYPE    
    SYNTAX DisplayString
	MAX-ACCESS read-only
	STATUS current
    DESCRIPTION
        "Set The Link1 2R4 Power Status Alarm."
    ::= {link1OBPTrap 33}
	
--  1.3.6.1.4.1.47477.10.21.2.3.1
		-- 1.3.6.1.4.1.47477.10.21.2.3.1
		link2_State OBJECT-TYPE
			SYNTAX INTEGER
				{
				off(0),
				on(1)
				}
			MAX-ACCESS read-only
			STATUS current
			DESCRIPTION
				"get the information about whether link2 is working."
			::= { link2OBP 1 }

		
--  1.3.6.1.4.1.47477.10.21.2.3.2
		-- 1.3.6.1.4.1.47477.10.21.2.3.2
		link2_DeviceType OBJECT-TYPE
			SYNTAX DisplayString
			MAX-ACCESS read-only
			STATUS current
			DESCRIPTION
				"get the type of card in link2."
			::= { link2OBP 2 }

			
--  1.3.6.1.4.1.47477.10.21.2.3.3
		-- 1.3.6.1.4.1.47477.10.21.2.3.3
		link2_WorkMode OBJECT-TYPE
			SYNTAX INTEGER
				{
				manualMode(0),
				autoMode(1)
				}
			MAX-ACCESS read-write
			STATUS current
			DESCRIPTION
				"get or set link2's work mode."
			::= { link2OBP 3 }

		
--  1.3.6.1.4.1.47477.10.21.2.3.4
		-- 1.3.6.1.4.1.47477.10.21.2.3.4
		link2_Channel OBJECT-TYPE
			SYNTAX INTEGER
				{
				bypass(0),
				primary(1)
				}
			MAX-ACCESS read-write
			STATUS current
			DESCRIPTION
				"get or set the channel in which link2 works."
			::= { link2OBP 4 }


--  1.3.6.1.4.1.47477.10.21.2.3.5
		-- 1.3.6.1.4.1.47477.10.21.2.3.5
		link2_R1Power OBJECT-TYPE
			SYNTAX DisplayString
			MAX-ACCESS read-only
			STATUS current
			DESCRIPTION
				"get the power of R1 in link2."
			::= { link2OBP 5 }

		
--  1.3.6.1.4.1.47477.10.21.2.3.6
		-- 1.3.6.1.4.1.47477.10.21.2.3.6
		link2_R2Power OBJECT-TYPE
			SYNTAX DisplayString
			MAX-ACCESS read-only
			STATUS current
			DESCRIPTION
				"get the power of R2 in link2."
			::= { link2OBP 6 }
			
--  1.3.6.1.4.1.47477.10.21.2.3.35
		-- 1.3.6.1.4.1.47477.10.21.2.3.35
		link2_R3Power OBJECT-TYPE
			SYNTAX DisplayString
			MAX-ACCESS read-only
			STATUS current
			DESCRIPTION
				"get the power of R3 in link2."
			::= { link2OBP 35 }
			
--  1.3.6.1.4.1.47477.10.21.2.3.36
		-- 1.3.6.1.4.1.47477.10.21.2.3.36
		link2_R4Power OBJECT-TYPE
			SYNTAX DisplayString
			MAX-ACCESS read-only
			STATUS current
			DESCRIPTION
				"get the power of R4 in link2."
			::= { link2OBP 36 }		
		
--  1.3.6.1.4.1.47477.10.21.2.3.7
		-- 1.3.6.1.4.1.47477.10.21.2.3.7
		link2_R1Wave OBJECT-TYPE
			SYNTAX INTEGER
				{
				w1310nm(0),
				w1550nm(1),
				na(2)
				}
			MAX-ACCESS read-write
			STATUS current
			DESCRIPTION
				"get or set the wave length of R1 in link2."
			::= { link2OBP 7 }

		
--  1.3.6.1.4.1.47477.10.21.2.3.8
		-- 1.3.6.1.4.1.47477.10.21.2.3.8
		link2_R2Wave OBJECT-TYPE
			SYNTAX INTEGER
				{
				w1310nm(0),
				w1550nm(1),
				na(2)
				}
			MAX-ACCESS read-write
			STATUS current
			DESCRIPTION
				"get or set the wave length of R2 in link2."
			::= { link2OBP 8 }


--  1.3.6.1.4.1.47477.10.21.2.3.27
		-- 1.3.6.1.4.1.47477.10.21.2.3.27
		link2_R3Wave OBJECT-TYPE
			SYNTAX INTEGER
				{
				w1310nm(0),
				w1550nm(1),
				na(2)
				}
			MAX-ACCESS read-write
			STATUS current
			DESCRIPTION
				"get or set the wave length of R3 in link2."
			::= { link2OBP 27 }

		
--  1.3.6.1.4.1.47477.10.21.2.3.28
		-- 1.3.6.1.4.1.47477.10.21.2.3.28
		link2_R4Wave OBJECT-TYPE
			SYNTAX INTEGER
				{
				w1310nm(0),
				w1550nm(1),
				na(2)
				}
			MAX-ACCESS read-write
			STATUS current
			DESCRIPTION
				"get or set the wave length of R4 in link2."
			::= { link2OBP 28 }
			
--  1.3.6.1.4.1.47477.10.21.2.3.9
		-- 1.3.6.1.4.1.47477.10.21.2.3.9
		link2_R1AlarmPower OBJECT-TYPE
			SYNTAX DisplayString
			MAX-ACCESS read-write
			STATUS current
			DESCRIPTION
				"get or set the power alarm threshold of R1 in link2."
			::= { link2OBP 9 }

		
--  1.3.6.1.4.1.47477.10.21.2.3.10
		-- 1.3.6.1.4.1.47477.10.21.2.3.10
		link2_R2AlarmPower OBJECT-TYPE
			SYNTAX DisplayString
			MAX-ACCESS read-write
			STATUS current
			DESCRIPTION
				"get or set the power alarm threshold of R2 in link2."
			::= { link2OBP 10 }


--  1.3.6.1.4.1.47477.10.21.2.3.29
		-- 1.3.6.1.4.1.47477.10.21.2.3.29
		link2_R3AlarmPower OBJECT-TYPE
			SYNTAX DisplayString
			MAX-ACCESS read-write
			STATUS current
			DESCRIPTION
				"get or set the power alarm threshold of R3 in link2."
			::= { link2OBP 29 }

		
--  1.3.6.1.4.1.47477.10.21.2.3.30
		-- 1.3.6.1.4.1.47477.10.21.2.3.30
		link2_R4AlarmPower OBJECT-TYPE
			SYNTAX DisplayString
			MAX-ACCESS read-write
			STATUS current
			DESCRIPTION
				"get or set the power alarm threshold of R4 in link2."
			::= { link2OBP 30 }

-- OBP4
--  1.3.6.1.4.1.47477.10.21.2.3.37
		-- 1.3.6.1.4.1.47477.10.21.2.3.37
		link2_1R1Power OBJECT-TYPE
			SYNTAX DisplayString
			MAX-ACCESS read-only
			STATUS current
			DESCRIPTION
				"get the power of 1R1 in link2."
			::= { link2OBP 37 }
			
--  1.3.6.1.4.1.47477.10.21.2.3.38
		-- 1.3.6.1.4.1.47477.10.21.2.3.38
		link2_1R2Power OBJECT-TYPE
			SYNTAX DisplayString
			MAX-ACCESS read-only
			STATUS current
			DESCRIPTION
				"get the power of 1R2 in link2."
			::= { link2OBP 38 }

--  1.3.6.1.4.1.47477.10.21.2.3.39
		-- 1.3.6.1.4.1.47477.10.21.2.3.39
		link2_1R3Power OBJECT-TYPE
			SYNTAX DisplayString
			MAX-ACCESS read-only
			STATUS current
			DESCRIPTION
				"get the power of 1R3 in link2."
			::= { link2OBP 39 }
			
--  1.3.6.1.4.1.47477.10.21.2.3.40
		-- 1.3.6.1.4.1.47477.10.21.2.3.40
		link2_1R4Power OBJECT-TYPE
			SYNTAX DisplayString
			MAX-ACCESS read-only
			STATUS current
			DESCRIPTION
				"get the power of 1R4 in link2."
			::= { link2OBP 40 }

--  1.3.6.1.4.1.47477.10.21.2.3.41
		-- 1.3.6.1.4.1.47477.10.21.2.3.41
		link2_2R1Power OBJECT-TYPE
			SYNTAX DisplayString
			MAX-ACCESS read-only
			STATUS current
			DESCRIPTION
				"get the power of 2R1 in link2."
			::= { link2OBP 41 }
			
--  1.3.6.1.4.1.47477.10.21.2.3.42
		-- 1.3.6.1.4.1.47477.10.21.2.3.42
		link2_2R2Power OBJECT-TYPE
			SYNTAX DisplayString
			MAX-ACCESS read-only
			STATUS current
			DESCRIPTION
				"get the power of 2R2 in link2."
			::= { link2OBP 42 }

--  1.3.6.1.4.1.47477.10.21.2.3.41
		-- 1.3.6.1.4.1.47477.10.21.2.3.43
		link2_2R3Power OBJECT-TYPE
			SYNTAX DisplayString
			MAX-ACCESS read-only
			STATUS current
			DESCRIPTION
				"get the power of 2R3 in link2."
			::= { link2OBP 43 }
			
--  1.3.6.1.4.1.47477.10.21.2.3.42
		-- 1.3.6.1.4.1.47477.10.21.2.3.44
		link2_2R4Power OBJECT-TYPE
			SYNTAX DisplayString
			MAX-ACCESS read-only
			STATUS current
			DESCRIPTION
				"get the power of 2R4 in link2."
			::= { link2OBP 44 }
			
--  1.3.6.1.4.1.47477.10.21.2.3.49
		-- 1.3.6.1.4.1.47477.10.21.2.3.49
		link2_1R1Wave OBJECT-TYPE
			SYNTAX INTEGER
				{
				w850nm(0),
				na(2)
				}
			MAX-ACCESS read-only
			STATUS current
			DESCRIPTION
				"get the wave length of 1R1 in link2."
			::= { link2OBP 49 }
		
--  1.3.6.1.4.1.47477.10.21.2.3.60
		-- 1.3.6.1.4.1.47477.10.21.2.3.60
		link2_1R2Wave OBJECT-TYPE
			SYNTAX INTEGER
				{
				w850nm(0),
				na(2)
				}
			MAX-ACCESS read-only
			STATUS current
			DESCRIPTION
				"get the wave length of 1R2 in link2."
			::= { link2OBP 60 }

--  1.3.6.1.4.1.47477.10.21.2.3.61
		-- 1.3.6.1.4.1.47477.10.21.2.3.61
		link2_1R3Wave OBJECT-TYPE
			SYNTAX INTEGER
				{
				w850nm(0),
				na(2)
				}
			MAX-ACCESS read-only
			STATUS current
			DESCRIPTION
				"get the wave length of 1R3 in link2."
			::= { link2OBP 61 }

		
--  1.3.6.1.4.1.47477.10.21.2.3.62
		-- 1.3.6.1.4.1.47477.10.21.2.3.62
		link2_1R4Wave OBJECT-TYPE
			SYNTAX INTEGER
				{
				w850nm(0),
				na(2)
				}
			MAX-ACCESS read-only
			STATUS current
			DESCRIPTION
				"get the wave length of 1R4 in link2."
			::= { link2OBP 62 }
	
--  1.3.6.1.4.1.47477.10.21.2.3.63
		-- 1.3.6.1.4.1.47477.10.21.2.3.63
		link2_2R1Wave OBJECT-TYPE
			SYNTAX INTEGER
				{
				w850nm(0),
				na(2)
				}
			MAX-ACCESS read-only
			STATUS current
			DESCRIPTION
				"get the wave length of 2R1 in link2."
			::= { link2OBP 63 }

		
--  1.3.6.1.4.1.47477.10.21.2.3.64
		-- 1.3.6.1.4.1.47477.10.21.2.3.64
		link2_2R2Wave OBJECT-TYPE
			SYNTAX INTEGER
				{
				w850nm(0),
				na(2)
				}
			MAX-ACCESS read-only
			STATUS current
			DESCRIPTION
				"get the wave length of 2R2 in link2."
			::= { link2OBP 64 }	
	
--  1.3.6.1.4.1.47477.10.21.2.3.65
		-- 1.3.6.1.4.1.47477.10.21.2.3.65
		link2_2R3Wave OBJECT-TYPE
			SYNTAX INTEGER
				{
				w850nm(0),
				na(2)
				}
			MAX-ACCESS read-only
			STATUS current
			DESCRIPTION
				"get the wave length of 2R3 in link2."
			::= { link2OBP 65 }

		
--  1.3.6.1.4.1.47477.10.21.2.3.66
		-- 1.3.6.1.4.1.47477.10.21.2.3.66
		link2_2R4Wave OBJECT-TYPE
			SYNTAX INTEGER
				{
				w850nm(0),
				na(2)
				}
			MAX-ACCESS read-only
			STATUS current
			DESCRIPTION
				"get the wave length of 2R4 in link2."
			::= { link2OBP 66 }	
			
--  1.3.6.1.4.1.47477.10.21.2.3.31
		-- 1.3.6.1.4.1.47477.10.21.2.3.31
		link2_1R1AlarmPower OBJECT-TYPE
			SYNTAX DisplayString
			MAX-ACCESS read-write
			STATUS current
			DESCRIPTION
				"get or set the power alarm threshold of 1R1 in link2."
			::= { link2OBP 31 }
			
--  1.3.6.1.4.1.47477.10.21.2.3.32
		-- 1.3.6.1.4.1.47477.10.21.2.3.32
		link2_1R2AlarmPower OBJECT-TYPE
			SYNTAX DisplayString
			MAX-ACCESS read-write
			STATUS current
			DESCRIPTION
				"get or set the power alarm threshold of 1R2 in link2."
			::= { link2OBP 32 }

--  1.3.6.1.4.1.47477.10.21.2.3.33
		-- 1.3.6.1.4.1.47477.10.21.2.3.33
		link2_1R3AlarmPower OBJECT-TYPE
			SYNTAX DisplayString
			MAX-ACCESS read-write
			STATUS current
			DESCRIPTION
				"get or set the power alarm threshold of 1R3 in link2."
			::= { link2OBP 33 }
			
--  1.3.6.1.4.1.47477.10.21.2.3.34
		-- 1.3.6.1.4.1.47477.10.21.2.3.34
		link2_1R4AlarmPower OBJECT-TYPE
			SYNTAX DisplayString
			MAX-ACCESS read-write
			STATUS current
			DESCRIPTION
				"get or set the power alarm threshold of 1R4 in link2."
			::= { link2OBP 34 }

--  1.3.6.1.4.1.47477.10.21.2.3.45
		-- 1.3.6.1.4.1.47477.10.21.2.3.45
		link2_2R1AlarmPower OBJECT-TYPE
			SYNTAX DisplayString
			MAX-ACCESS read-write
			STATUS current
			DESCRIPTION
				"get or set the power alarm threshold of 2R1 in link2."
			::= { link2OBP 45 }
			
--  1.3.6.1.4.1.47477.10.21.2.3.46
		-- 1.3.6.1.4.1.47477.10.21.2.3.46
		link2_2R2AlarmPower OBJECT-TYPE
			SYNTAX DisplayString
			MAX-ACCESS read-write
			STATUS current
			DESCRIPTION
				"get or set the power alarm threshold of 2R2 in link2."
			::= { link2OBP 46 }

--  1.3.6.1.4.1.47477.10.21.2.3.47
		-- 1.3.6.1.4.1.47477.10.21.2.3.47
		link2_2R3AlarmPower OBJECT-TYPE
			SYNTAX DisplayString
			MAX-ACCESS read-write
			STATUS current
			DESCRIPTION
				"get or set the power alarm threshold of 2R3 in link2."
			::= { link2OBP 47 }
			
--  1.3.6.1.4.1.47477.10.21.2.3.48
		-- 1.3.6.1.4.1.47477.10.21.2.3.48
		link2_2R4AlarmPower OBJECT-TYPE
			SYNTAX DisplayString
			MAX-ACCESS read-write
			STATUS current
			DESCRIPTION
				"get or set the power alarm threshold of 2R4 in link2."
			::= { link2OBP 48 }
			
--  1.3.6.1.4.1.47477.10.21.2.3.11
		-- 1.3.6.1.4.1.47477.10.21.2.3.11
		link2_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link2OBP 11 }
			
--  1.3.6.1.4.1.47477.10.21.2.3.67
		-- 1.3.6.1.4.1.47477.10.21.2.3.67
		link2_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link2OBP 67 }
			
--  1.3.6.1.4.1.47477.10.21.2.3.68
		-- 1.3.6.1.4.1.47477.10.21.2.3.68
		link2_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link2OBP 68 }
			
--  1.3.6.1.4.1.47477.10.21.2.3.12
		-- 1.3.6.1.4.1.47477.10.21.2.3.12
		link2_ReturnDelay OBJECT-TYPE
			--SYNTAX Integer32
			SYNTAX Integer32
			MAX-ACCESS read-write
			STATUS current
			DESCRIPTION
				"get or set how long link2 takes to return to automatic mode."
			::= { link2OBP 12 }
			
--  1.3.6.1.4.1.47477.10.21.2.3.13
		-- 1.3.6.1.4.1.47477.10.21.2.3.13
		link2_BackMode OBJECT-TYPE
			SYNTAX INTEGER
				{
				autoNoBack(0),
				autoBack(1)
				}
			MAX-ACCESS read-write
			STATUS current
			DESCRIPTION
				"get or set the back mode of link2."
			::= { link2OBP 13 }

		
--  1.3.6.1.4.1.47477.10.21.2.3.14
		-- 1.3.6.1.4.1.47477.10.21.2.3.14
		link2_BackDelay OBJECT-TYPE
			SYNTAX Integer32
			MAX-ACCESS read-write
			STATUS current
			DESCRIPTION
				"get or set the back delay."
			::= { link2OBP 14 }

--  1.3.6.1.4.1.47477.10.21.2.3.15
		-- 1.3.6.1.4.1.47477.10.21.2.3.15
		link2_ActiveHeartSwitch OBJECT-TYPE
			SYNTAX INTEGER
				{
				off(0),
				on(1)
				}
			MAX-ACCESS read-write
			STATUS current
			DESCRIPTION
				"get or set the switch status of active heartbeat."
			::= { link2OBP 15 }

		
--  1.3.6.1.4.1.47477.10.21.2.3.16
		-- 1.3.6.1.4.1.47477.10.21.2.3.16
		link2_ActiveSendInterval OBJECT-TYPE
			SYNTAX Integer32
			MAX-ACCESS read-write
			STATUS current
			DESCRIPTION
				"get or set the send interval of active heartbeat."
			::= { link2OBP 16 }		

--  1.3.6.1.4.1.47477.10.21.2.3.17
		-- 1.3.6.1.4.1.47477.10.21.2.3.17
		link2_ActiveTimeOut OBJECT-TYPE
			SYNTAX Integer32
			MAX-ACCESS read-write
			STATUS current
			DESCRIPTION
				"get or set how long the active heartbeat send timeout."
			::= { link2OBP 17 }

--  1.3.6.1.4.1.47477.10.21.2.3.18
		-- 1.3.6.1.4.1.47477.10.21.2.3.18
		link2_ActiveLossBypass OBJECT-TYPE
			SYNTAX Integer32
			MAX-ACCESS read-write
			STATUS current
			DESCRIPTION
				"get or set the bypass for active heartbeat packet loss."
			::= { link2OBP 18 }

--  1.3.6.1.4.1.47477.10.21.2.3.19
		-- 1.3.6.1.4.1.47477.10.21.2.3.19
		link2_PingIpAddress OBJECT-TYPE
			SYNTAX IpAddress
			MAX-ACCESS read-write
			STATUS current
			DESCRIPTION
				"get or set the ping ip address of link2."
			::= { link2OBP 19 }

--  1.3.6.1.4.1.47477.10.21.2.3.20
		-- 1.3.6.1.4.1.47477.10.21.2.3.20
		link2_PassiveHeartSwitch OBJECT-TYPE
			SYNTAX INTEGER
				{
				off(0),
				on(1)
				}
			MAX-ACCESS read-write
			STATUS current
			DESCRIPTION
				"get or set the switch status of passive heartbeat."
			::= { link2OBP 20 }
	

--  1.3.6.1.4.1.47477.10.21.2.3.21
		-- 1.3.6.1.4.1.47477.10.21.2.3.21
		link2_PassiveTimeOut OBJECT-TYPE
			SYNTAX Integer32
			MAX-ACCESS read-write
			STATUS current
			DESCRIPTION
				"get or set how long the passive heartbeat send timeout."
			::= { link2OBP 21 }

--  1.3.6.1.4.1.47477.10.21.2.3.22
		-- 1.3.6.1.4.1.47477.10.21.2.3.22
		link2_PassiveLossBypass OBJECT-TYPE
			SYNTAX Integer32
			MAX-ACCESS read-write
			STATUS current
			DESCRIPTION
				"get or set the bypass for passive heartbeat packet loss."
			::= { link2OBP 22 }

--  1.3.6.1.4.1.47477.10.21.2.3.23
		-- 1.3.6.1.4.1.47477.10.21.2.3.23
		link2_SwitchProtect OBJECT-TYPE
			SYNTAX INTEGER
				{
				off(0),
				on(1)
				}
			MAX-ACCESS read-write
			STATUS current
			DESCRIPTION
				"get or set the switch protection status of link2."
			::= { link2OBP 23 }
			
--  1.3.6.1.4.1.47477.10.21.2.3.24
		-- 1.3.6.1.4.1.47477.10.21.2.3.24
		link2_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link2OBP 24 }		

--  1.3.6.1.4.1.47477.10.21.2.3.25
		-- 1.3.6.1.4.1.47477.10.21.2.3.25
		link2_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link2OBP 25 }	

--  1.3.6.1.4.1.47477.10.21.2.3.26
		-- 1.3.6.1.4.1.47477.10.21.2.3.26
		link2_PowerAlarmStatus OBJECT-TYPE
			SYNTAX INTEGER
				{
				off(0),
				alarm(1),
				normal(2),
				na(3)
				}
			MAX-ACCESS read-only
			STATUS current
			DESCRIPTION
				"get whether a power alarm is generated."
			::= { link2OBP 26 }	


-- 1.3.6.1.4.1.47477.10.21.2.3.50.1
	link2_WorkModeChange 	OBJECT-TYPE    
    SYNTAX INTEGER	{
				manualMode(0),
				autoMode(1)
		}
	MAX-ACCESS read-only
	STATUS current
    DESCRIPTION
        "The Link mode Changed."
    ::= {link2OBPTrap 1}

-- 1.3.6.1.4.1.47477.10.21.2.3.50.2
	link2_StateChange 	OBJECT-TYPE    
    SYNTAX INTEGER	{
				bypass(0),
				primary(1)
		}
	MAX-ACCESS read-only
	STATUS current
    DESCRIPTION
        "The Link State(Channel) Changed."
    ::= {link2OBPTrap 2}

-- 1.3.6.1.4.1.47477.10.21.2.3.50.3
	link2_R1WaveSet 	OBJECT-TYPE    
    SYNTAX INTEGER	{
				w1310nm(0),
				w1550nm(1)
		}
	MAX-ACCESS read-only
	STATUS current
    DESCRIPTION
        "Set The link2 R1 Wave."
    ::= {link2OBPTrap 3}

-- 1.3.6.1.4.1.47477.10.21.2.3.50.4
	link2_R2WaveSet 	OBJECT-TYPE    
    SYNTAX INTEGER	{
				w1310nm(0),
				w1550nm(1)
		}
	MAX-ACCESS read-only
	STATUS current
    DESCRIPTION
        "Set The link2 R2 Wave."
    ::= {link2OBPTrap 4}			

-- 1.3.6.1.4.1.47477.10.21.2.3.50.5
	link2_R3WaveSet 	OBJECT-TYPE    
    SYNTAX INTEGER	{
				w1310nm(0),
				w1550nm(1)
		}
	MAX-ACCESS read-only
	STATUS current
    DESCRIPTION
        "Set The link2 R3 Wave."
    ::= {link2OBPTrap 5}

-- 1.3.6.1.4.1.47477.10.21.2.3.50.6
	link2_R4WaveSet 	OBJECT-TYPE    
    SYNTAX INTEGER	{
				w1310nm(0),
				w1550nm(1)
		}
	MAX-ACCESS read-only
	STATUS current
    DESCRIPTION
        "Set The link2 R4 Wave."
    ::= {link2OBPTrap 6}	
	
-- 1.3.6.1.4.1.47477.10.21.2.3.50.7
	link2_R1AlarmSet 	OBJECT-TYPE    
    SYNTAX DisplayString
	MAX-ACCESS read-only
	STATUS current
    DESCRIPTION
        "Set The link2 R1 Alarm Threshold."
    ::= {link2OBPTrap 7}

-- 1.3.6.1.4.1.47477.10.21.2.3.50.8
	link2_R2AlarmSet 	OBJECT-TYPE    
    SYNTAX DisplayString
	MAX-ACCESS read-only
	STATUS current
    DESCRIPTION
        "Set The link2 R2 Alarm Threshold."
    ::= {link2OBPTrap 8}
	
-- 1.3.6.1.4.1.47477.10.21.2.3.50.9
	link2_R3AlarmSet 	OBJECT-TYPE    
    SYNTAX DisplayString
	MAX-ACCESS read-only
	STATUS current
    DESCRIPTION
        "Set The link2 R3 Alarm Threshold."
    ::= {link2OBPTrap 9}

-- 1.3.6.1.4.1.47477.10.21.2.3.50.10
	link2_R4AlarmSet 	OBJECT-TYPE    
    SYNTAX DisplayString
	MAX-ACCESS read-only
	STATUS current
    DESCRIPTION
        "Set The link2 R4 Alarm Threshold."
    ::= {link2OBPTrap 10}	
	
	
-- 1.3.6.1.4.1.47477.10.21.2.3.50.11
	link2_1R1AlarmSet 	OBJECT-TYPE    
    SYNTAX DisplayString
	MAX-ACCESS read-only
	STATUS current
    DESCRIPTION
        "Set The link2 1R1 Alarm Threshold."
    ::= {link2OBPTrap 11}

-- 1.3.6.1.4.1.47477.10.21.2.3.50.12
	link2_2R1AlarmSet 	OBJECT-TYPE    
    SYNTAX DisplayString
	MAX-ACCESS read-only
	STATUS current
    DESCRIPTION
        "Set The link2 2R1 Alarm Threshold."
    ::= {link2OBPTrap 12}
	
-- 1.3.6.1.4.1.47477.10.21.2.3.50.13
	link2_1R2AlarmSet 	OBJECT-TYPE    
    SYNTAX DisplayString
	MAX-ACCESS read-only
	STATUS current
    DESCRIPTION
        "Set The link2 1R2 Alarm Threshold."
    ::= {link2OBPTrap 13}

-- 1.3.6.1.4.1.47477.10.21.2.3.50.14
	link2_2R2AlarmSet 	OBJECT-TYPE    
    SYNTAX DisplayString
	MAX-ACCESS read-only
	STATUS current
    DESCRIPTION
        "Set The link2 2R2 Alarm Threshold."
    ::= {link2OBPTrap 14}
	
-- 1.3.6.1.4.1.47477.10.21.2.3.50.15
	link2_1R3AlarmSet 	OBJECT-TYPE    
    SYNTAX DisplayString
	MAX-ACCESS read-only
	STATUS current
    DESCRIPTION
        "Set The link2 1R3 Alarm Threshold."
    ::= {link2OBPTrap 15}

-- 1.3.6.1.4.1.47477.10.21.2.3.50.16
	link2_2R3AlarmSet 	OBJECT-TYPE    
    SYNTAX DisplayString
	MAX-ACCESS read-only
	STATUS current
    DESCRIPTION
        "Set The link2 2R3 Alarm Threshold."
    ::= {link2OBPTrap 16}
	
-- 1.3.6.1.4.1.47477.10.21.2.3.50.17
	link2_1R4AlarmSet 	OBJECT-TYPE    
    SYNTAX DisplayString
	MAX-ACCESS read-only
	STATUS current
    DESCRIPTION
        "Set The link2 1R4 Alarm Threshold."
    ::= {link2OBPTrap 17}

-- 1.3.6.1.4.1.47477.10.21.2.3.50.18
	link2_2R4AlarmSet 	OBJECT-TYPE    
    SYNTAX DisplayString
	MAX-ACCESS read-only
	STATUS current
    DESCRIPTION
        "Set The link2 2R4 Alarm Threshold."
    ::= {link2OBPTrap 18}
	
-- 1.3.6.1.4.1.47477.10.21.2.3.50.19
	link2_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link2 PowerAlarmBypass2 Changed."
    ::= {link2OBPTrap 19}
	
-- 1.3.6.1.4.1.47477.10.21.2.3.50.20
	link2_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link2 PowerAlarmBypass4 Changed."
    ::= {link2OBPTrap 20}	
	
-- 1.3.6.1.4.1.47477.10.21.2.3.50.21
	link2_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link2 PowerAlarmBypass8 Changed."
    ::= {link2OBPTrap 21}
	
-- 1.3.6.1.4.1.47477.10.21.2.3.50.22
	link2_powerAlarmR1 	OBJECT-TYPE    
    SYNTAX DisplayString
	MAX-ACCESS read-only
	STATUS current
    DESCRIPTION
        "Set The link2 R1 Power Status Alarm."
    ::= {link2OBPTrap 22}
	
-- 1.3.6.1.4.1.47477.10.21.2.3.50.23
	link2_powerAlarmR2 	OBJECT-TYPE    
    SYNTAX DisplayString
	MAX-ACCESS read-only
	STATUS current
    DESCRIPTION
        "Set The link2 R2 Power Status Alarm."
    ::= {link2OBPTrap 23}
	
-- 1.3.6.1.4.1.47477.10.21.2.3.50.24
	link2_powerAlarmR3 	OBJECT-TYPE    
    SYNTAX DisplayString
	MAX-ACCESS read-only
	STATUS current
    DESCRIPTION
        "Set The link2 R3 Power Status Alarm."
    ::= {link2OBPTrap 24}
	
-- 1.3.6.1.4.1.47477.10.21.2.3.50.25
	link2_powerAlarmR4 	OBJECT-TYPE    
    SYNTAX DisplayString
	MAX-ACCESS read-only
	STATUS current
    DESCRIPTION
        "Set The link2 R4 Power Status Alarm."
    ::= {link2OBPTrap 25}
	
	
-- 1.3.6.1.4.1.47477.10.21.2.3.50.26
	link2_powerAlarm1R1 	OBJECT-TYPE    
    SYNTAX DisplayString
	MAX-ACCESS read-only
	STATUS current
    DESCRIPTION
        "Set The link2 1R1 Power Status Alarm."
    ::= {link2OBPTrap 26}
	
-- 1.3.6.1.4.1.47477.10.21.2.3.50.27
	link2_powerAlarm2R1 	OBJECT-TYPE    
    SYNTAX DisplayString
	MAX-ACCESS read-only
	STATUS current
    DESCRIPTION
        "Set The link2 2R1 Power Status Alarm."
    ::= {link2OBPTrap 27}
	
-- 1.3.6.1.4.1.47477.10.21.2.3.50.28
	link2_powerAlarm1R2 	OBJECT-TYPE    
    SYNTAX DisplayString
	MAX-ACCESS read-only
	STATUS current
    DESCRIPTION
        "Set The link2 1R2 Power Status Alarm."
    ::= {link2OBPTrap 28}
	
-- 1.3.6.1.4.1.47477.10.21.2.3.50.29
	link2_powerAlarm2R2 	OBJECT-TYPE    
    SYNTAX DisplayString
	MAX-ACCESS read-only
	STATUS current
    DESCRIPTION
        "Set The link2 2R2 Power Status Alarm."
    ::= {link2OBPTrap 29}
	
-- 1.3.6.1.4.1.47477.10.21.2.3.50.30
	link2_powerAlarm1R3 	OBJECT-TYPE    
    SYNTAX DisplayString
	MAX-ACCESS read-only
	STATUS current
    DESCRIPTION
        "Set The link2 1R3 Power Status Alarm."
    ::= {link2OBPTrap 30}
	
-- 1.3.6.1.4.1.47477.10.21.2.3.50.31
	link2_powerAlarm2R3 	OBJECT-TYPE    
    SYNTAX DisplayString
	MAX-ACCESS read-only
	STATUS current
    DESCRIPTION
        "Set The link2 2R1 Power Status Alarm."
    ::= {link2OBPTrap 31}
	
-- 1.3.6.1.4.1.47477.10.21.2.3.50.32
	link2_powerAlarm1R4 	OBJECT-TYPE    
    SYNTAX DisplayString
	MAX-ACCESS read-only
	STATUS current
    DESCRIPTION
        "Set The link2 1R4 Power Status Alarm."
    ::= {link2OBPTrap 32}
	
-- 1.3.6.1.4.1.47477.10.21.2.3.50.33
	link2_powerAlarm2R4 	OBJECT-TYPE    
    SYNTAX DisplayString
	MAX-ACCESS read-only
	STATUS current
    DESCRIPTION
        "Set The link2 2R4 Power Status Alarm."
    ::= {link2OBPTrap 33}
	
--  1.3.6.1.4.1.47477.10.21.3.3.1
		-- 1.3.6.1.4.1.47477.10.21.3.3.1
		link3_State OBJECT-TYPE
			SYNTAX INTEGER
				{
				off(0),
				on(1)
				}
			MAX-ACCESS read-only
			STATUS current
			DESCRIPTION
				"get the information about whether link3 is working."
			::= { link3OBP 1 }

		
--  1.3.6.1.4.1.47477.10.21.3.3.2
		-- 1.3.6.1.4.1.47477.10.21.3.3.2
		link3_DeviceType OBJECT-TYPE
			SYNTAX DisplayString
			MAX-ACCESS read-only
			STATUS current
			DESCRIPTION
				"get the type of card in link3."
			::= { link3OBP 2 }

			
--  1.3.6.1.4.1.47477.10.21.3.3.3
		-- 1.3.6.1.4.1.47477.10.21.3.3.3
		link3_WorkMode OBJECT-TYPE
			SYNTAX INTEGER
				{
				manualMode(0),
				autoMode(1)
				}
			MAX-ACCESS read-write
			STATUS current
			DESCRIPTION
				"get or set link3's work mode."
			::= { link3OBP 3 }

		
--  1.3.6.1.4.1.47477.10.21.3.3.4
		-- 1.3.6.1.4.1.47477.10.21.3.3.4
		link3_Channel OBJECT-TYPE
			SYNTAX INTEGER
				{
				bypass(0),
				primary(1)
				}
			MAX-ACCESS read-write
			STATUS current
			DESCRIPTION
				"get or set the channel in which link3 works."
			::= { link3OBP 4 }


--  1.3.6.1.4.1.47477.10.21.3.3.5
		-- 1.3.6.1.4.1.47477.10.21.3.3.5
		link3_R1Power OBJECT-TYPE
			SYNTAX DisplayString
			MAX-ACCESS read-only
			STATUS current
			DESCRIPTION
				"get the power of R1 in link3."
			::= { link3OBP 5 }

		
--  1.3.6.1.4.1.47477.10.21.3.3.6
		-- 1.3.6.1.4.1.47477.10.21.3.3.6
		link3_R2Power OBJECT-TYPE
			SYNTAX DisplayString
			MAX-ACCESS read-only
			STATUS current
			DESCRIPTION
				"get the power of R2 in link3."
			::= { link3OBP 6 }
			
--  1.3.6.1.4.1.47477.10.21.3.3.35
		-- 1.3.6.1.4.1.47477.10.21.3.3.35
		link3_R3Power OBJECT-TYPE
			SYNTAX DisplayString
			MAX-ACCESS read-only
			STATUS current
			DESCRIPTION
				"get the power of R3 in link3."
			::= { link3OBP 35 }
			
--  1.3.6.1.4.1.47477.10.21.3.3.36
		-- 1.3.6.1.4.1.47477.10.21.3.3.36
		link3_R4Power OBJECT-TYPE
			SYNTAX DisplayString
			MAX-ACCESS read-only
			STATUS current
			DESCRIPTION
				"get the power of R4 in link3."
			::= { link3OBP 36 }		
		
--  1.3.6.1.4.1.47477.10.21.3.3.7
		-- 1.3.6.1.4.1.47477.10.21.3.3.7
		link3_R1Wave OBJECT-TYPE
			SYNTAX INTEGER
				{
				w1310nm(0),
				w1550nm(1),
				na(2)
				}
			MAX-ACCESS read-write
			STATUS current
			DESCRIPTION
				"get or set the wave length of R1 in link3."
			::= { link3OBP 7 }

		
--  1.3.6.1.4.1.47477.10.21.3.3.8
		-- 1.3.6.1.4.1.47477.10.21.3.3.8
		link3_R2Wave OBJECT-TYPE
			SYNTAX INTEGER
				{
				w1310nm(0),
				w1550nm(1),
				na(2)
				}
			MAX-ACCESS read-write
			STATUS current
			DESCRIPTION
				"get or set the wave length of R2 in link3."
			::= { link3OBP 8 }


--  1.3.6.1.4.1.47477.10.21.3.3.27
		-- 1.3.6.1.4.1.47477.10.21.3.3.27
		link3_R3Wave OBJECT-TYPE
			SYNTAX INTEGER
				{
				w1310nm(0),
				w1550nm(1),
				na(2)
				}
			MAX-ACCESS read-write
			STATUS current
			DESCRIPTION
				"get or set the wave length of R3 in link3."
			::= { link3OBP 27 }

		
--  1.3.6.1.4.1.47477.10.21.3.3.28
		-- 1.3.6.1.4.1.47477.10.21.3.3.28
		link3_R4Wave OBJECT-TYPE
			SYNTAX INTEGER
				{
				w1310nm(0),
				w1550nm(1),
				na(2)
				}
			MAX-ACCESS read-write
			STATUS current
			DESCRIPTION
				"get or set the wave length of R4 in link3."
			::= { link3OBP 28 }
			
--  1.3.6.1.4.1.47477.10.21.3.3.9
		-- 1.3.6.1.4.1.47477.10.21.3.3.9
		link3_R1AlarmPower OBJECT-TYPE
			SYNTAX DisplayString
			MAX-ACCESS read-write
			STATUS current
			DESCRIPTION
				"get or set the power alarm threshold of R1 in link3."
			::= { link3OBP 9 }

		
--  1.3.6.1.4.1.47477.10.21.3.3.10
		-- 1.3.6.1.4.1.47477.10.21.3.3.10
		link3_R2AlarmPower OBJECT-TYPE
			SYNTAX DisplayString
			MAX-ACCESS read-write
			STATUS current
			DESCRIPTION
				"get or set the power alarm threshold of R2 in link3."
			::= { link3OBP 10 }


--  1.3.6.1.4.1.47477.10.21.3.3.29
		-- 1.3.6.1.4.1.47477.10.21.3.3.29
		link3_R3AlarmPower OBJECT-TYPE
			SYNTAX DisplayString
			MAX-ACCESS read-write
			STATUS current
			DESCRIPTION
				"get or set the power alarm threshold of R3 in link3."
			::= { link3OBP 29 }

		
--  1.3.6.1.4.1.47477.10.21.3.3.30
		-- 1.3.6.1.4.1.47477.10.21.3.3.30
		link3_R4AlarmPower OBJECT-TYPE
			SYNTAX DisplayString
			MAX-ACCESS read-write
			STATUS current
			DESCRIPTION
				"get or set the power alarm threshold of R4 in link3."
			::= { link3OBP 30 }

-- OBP4
--  1.3.6.1.4.1.47477.10.21.3.3.37
		-- 1.3.6.1.4.1.47477.10.21.3.3.37
		link3_1R1Power OBJECT-TYPE
			SYNTAX DisplayString
			MAX-ACCESS read-only
			STATUS current
			DESCRIPTION
				"get the power of 1R1 in link3."
			::= { link3OBP 37 }
			
--  1.3.6.1.4.1.47477.10.21.3.3.38
		-- 1.3.6.1.4.1.47477.10.21.3.3.38
		link3_1R2Power OBJECT-TYPE
			SYNTAX DisplayString
			MAX-ACCESS read-only
			STATUS current
			DESCRIPTION
				"get the power of 1R2 in link3."
			::= { link3OBP 38 }

--  1.3.6.1.4.1.47477.10.21.3.3.39
		-- 1.3.6.1.4.1.47477.10.21.3.3.39
		link3_1R3Power OBJECT-TYPE
			SYNTAX DisplayString
			MAX-ACCESS read-only
			STATUS current
			DESCRIPTION
				"get the power of 1R3 in link3."
			::= { link3OBP 39 }
			
--  1.3.6.1.4.1.47477.10.21.3.3.40
		-- 1.3.6.1.4.1.47477.10.21.3.3.40
		link3_1R4Power OBJECT-TYPE
			SYNTAX DisplayString
			MAX-ACCESS read-only
			STATUS current
			DESCRIPTION
				"get the power of 1R4 in link3."
			::= { link3OBP 40 }

--  1.3.6.1.4.1.47477.10.21.3.3.41
		-- 1.3.6.1.4.1.47477.10.21.3.3.41
		link3_2R1Power OBJECT-TYPE
			SYNTAX DisplayString
			MAX-ACCESS read-only
			STATUS current
			DESCRIPTION
				"get the power of 2R1 in link3."
			::= { link3OBP 41 }
			
--  1.3.6.1.4.1.47477.10.21.3.3.42
		-- 1.3.6.1.4.1.47477.10.21.3.3.42
		link3_2R2Power OBJECT-TYPE
			SYNTAX DisplayString
			MAX-ACCESS read-only
			STATUS current
			DESCRIPTION
				"get the power of 2R2 in link3."
			::= { link3OBP 42 }

--  1.3.6.1.4.1.47477.10.21.3.3.41
		-- 1.3.6.1.4.1.47477.10.21.3.3.43
		link3_2R3Power OBJECT-TYPE
			SYNTAX DisplayString
			MAX-ACCESS read-only
			STATUS current
			DESCRIPTION
				"get the power of 2R3 in link3."
			::= { link3OBP 43 }
			
--  1.3.6.1.4.1.47477.10.21.3.3.42
		-- 1.3.6.1.4.1.47477.10.21.3.3.44
		link3_2R4Power OBJECT-TYPE
			SYNTAX DisplayString
			MAX-ACCESS read-only
			STATUS current
			DESCRIPTION
				"get the power of 2R4 in link3."
			::= { link3OBP 44 }
			
--  1.3.6.1.4.1.47477.10.21.3.3.49
		-- 1.3.6.1.4.1.47477.10.21.3.3.49
		link3_1R1Wave OBJECT-TYPE
			SYNTAX INTEGER
				{
				w850nm(0),
				na(2)
				}
			MAX-ACCESS read-only
			STATUS current
			DESCRIPTION
				"get the wave length of 1R1 in link3."
			::= { link3OBP 49 }
		
--  1.3.6.1.4.1.47477.10.21.3.3.60
		-- 1.3.6.1.4.1.47477.10.21.3.3.60
		link3_1R2Wave OBJECT-TYPE
			SYNTAX INTEGER
				{
				w850nm(0),
				na(2)
				}
			MAX-ACCESS read-only
			STATUS current
			DESCRIPTION
				"get the wave length of 1R2 in link3."
			::= { link3OBP 60 }

--  1.3.6.1.4.1.47477.10.21.3.3.61
		-- 1.3.6.1.4.1.47477.10.21.3.3.61
		link3_1R3Wave OBJECT-TYPE
			SYNTAX INTEGER
				{
				w850nm(0),
				na(2)
				}
			MAX-ACCESS read-only
			STATUS current
			DESCRIPTION
				"get the wave length of 1R3 in link3."
			::= { link3OBP 61 }

		
--  1.3.6.1.4.1.47477.10.21.3.3.62
		-- 1.3.6.1.4.1.47477.10.21.3.3.62
		link3_1R4Wave OBJECT-TYPE
			SYNTAX INTEGER
				{
				w850nm(0),
				na(2)
				}
			MAX-ACCESS read-only
			STATUS current
			DESCRIPTION
				"get the wave length of 1R4 in link3."
			::= { link3OBP 62 }
	
--  1.3.6.1.4.1.47477.10.21.3.3.63
		-- 1.3.6.1.4.1.47477.10.21.3.3.63
		link3_2R1Wave OBJECT-TYPE
			SYNTAX INTEGER
				{
				w850nm(0),
				na(2)
				}
			MAX-ACCESS read-only
			STATUS current
			DESCRIPTION
				"get the wave length of 2R1 in link3."
			::= { link3OBP 63 }

		
--  1.3.6.1.4.1.47477.10.21.3.3.64
		-- 1.3.6.1.4.1.47477.10.21.3.3.64
		link3_2R2Wave OBJECT-TYPE
			SYNTAX INTEGER
				{
				w850nm(0),
				na(2)
				}
			MAX-ACCESS read-only
			STATUS current
			DESCRIPTION
				"get the wave length of 2R2 in link3."
			::= { link3OBP 64 }	
	
--  1.3.6.1.4.1.47477.10.21.3.3.65
		-- 1.3.6.1.4.1.47477.10.21.3.3.65
		link3_2R3Wave OBJECT-TYPE
			SYNTAX INTEGER
				{
				w850nm(0),
				na(2)
				}
			MAX-ACCESS read-only
			STATUS current
			DESCRIPTION
				"get the wave length of 2R3 in link3."
			::= { link3OBP 65 }

		
--  1.3.6.1.4.1.47477.10.21.3.3.66
		-- 1.3.6.1.4.1.47477.10.21.3.3.66
		link3_2R4Wave OBJECT-TYPE
			SYNTAX INTEGER
				{
				w850nm(0),
				na(2)
				}
			MAX-ACCESS read-only
			STATUS current
			DESCRIPTION
				"get the wave length of 2R4 in link3."
			::= { link3OBP 66 }	
			
--  1.3.6.1.4.1.47477.10.21.3.3.31
		-- 1.3.6.1.4.1.47477.10.21.3.3.31
		link3_1R1AlarmPower OBJECT-TYPE
			SYNTAX DisplayString
			MAX-ACCESS read-write
			STATUS current
			DESCRIPTION
				"get or set the power alarm threshold of 1R1 in link3."
			::= { link3OBP 31 }
			
--  1.3.6.1.4.1.47477.10.21.3.3.32
		-- 1.3.6.1.4.1.47477.10.21.3.3.32
		link3_1R2AlarmPower OBJECT-TYPE
			SYNTAX DisplayString
			MAX-ACCESS read-write
			STATUS current
			DESCRIPTION
				"get or set the power alarm threshold of 1R2 in link3."
			::= { link3OBP 32 }

--  1.3.6.1.4.1.47477.10.21.3.3.33
		-- 1.3.6.1.4.1.47477.10.21.3.3.33
		link3_1R3AlarmPower OBJECT-TYPE
			SYNTAX DisplayString
			MAX-ACCESS read-write
			STATUS current
			DESCRIPTION
				"get or set the power alarm threshold of 1R3 in link3."
			::= { link3OBP 33 }
			
--  1.3.6.1.4.1.47477.10.21.3.3.34
		-- 1.3.6.1.4.1.47477.10.21.3.3.34
		link3_1R4AlarmPower OBJECT-TYPE
			SYNTAX DisplayString
			MAX-ACCESS read-write
			STATUS current
			DESCRIPTION
				"get or set the power alarm threshold of 1R4 in link3."
			::= { link3OBP 34 }

--  1.3.6.1.4.1.47477.10.21.3.3.45
		-- 1.3.6.1.4.1.47477.10.21.3.3.45
		link3_2R1AlarmPower OBJECT-TYPE
			SYNTAX DisplayString
			MAX-ACCESS read-write
			STATUS current
			DESCRIPTION
				"get or set the power alarm threshold of 2R1 in link3."
			::= { link3OBP 45 }
			
--  1.3.6.1.4.1.47477.10.21.3.3.46
		-- 1.3.6.1.4.1.47477.10.21.3.3.46
		link3_2R2AlarmPower OBJECT-TYPE
			SYNTAX DisplayString
			MAX-ACCESS read-write
			STATUS current
			DESCRIPTION
				"get or set the power alarm threshold of 2R2 in link3."
			::= { link3OBP 46 }

--  1.3.6.1.4.1.47477.10.21.3.3.47
		-- 1.3.6.1.4.1.47477.10.21.3.3.47
		link3_2R3AlarmPower OBJECT-TYPE
			SYNTAX DisplayString
			MAX-ACCESS read-write
			STATUS current
			DESCRIPTION
				"get or set the power alarm threshold of 2R3 in link3."
			::= { link3OBP 47 }
			
--  1.3.6.1.4.1.47477.10.21.3.3.48
		-- 1.3.6.1.4.1.47477.10.21.3.3.48
		link3_2R4AlarmPower OBJECT-TYPE
			SYNTAX DisplayString
			MAX-ACCESS read-write
			STATUS current
			DESCRIPTION
				"get or set the power alarm threshold of 2R4 in link3."
			::= { link3OBP 48 }
			
--  1.3.6.1.4.1.47477.10.21.3.3.11
		-- 1.3.6.1.4.1.47477.10.21.3.3.11
		link3_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link3OBP 11 }
			
--  1.3.6.1.4.1.47477.10.21.3.3.67
		-- 1.3.6.1.4.1.47477.10.21.3.3.67
		link3_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link3OBP 67 }
			
--  1.3.6.1.4.1.47477.10.21.3.3.68
		-- 1.3.6.1.4.1.47477.10.21.3.3.68
		link3_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link3OBP 68 }
			
--  1.3.6.1.4.1.47477.10.21.3.3.12
		-- 1.3.6.1.4.1.47477.10.21.3.3.12
		link3_ReturnDelay OBJECT-TYPE
			--SYNTAX Integer32
			SYNTAX Integer32
			MAX-ACCESS read-write
			STATUS current
			DESCRIPTION
				"get or set how long link3 takes to return to automatic mode."
			::= { link3OBP 12 }
			
--  1.3.6.1.4.1.47477.10.21.3.3.13
		-- 1.3.6.1.4.1.47477.10.21.3.3.13
		link3_BackMode OBJECT-TYPE
			SYNTAX INTEGER
				{
				autoNoBack(0),
				autoBack(1)
				}
			MAX-ACCESS read-write
			STATUS current
			DESCRIPTION
				"get or set the back mode of link3."
			::= { link3OBP 13 }

		
--  1.3.6.1.4.1.47477.10.21.3.3.14
		-- 1.3.6.1.4.1.47477.10.21.3.3.14
		link3_BackDelay OBJECT-TYPE
			SYNTAX Integer32
			MAX-ACCESS read-write
			STATUS current
			DESCRIPTION
				"get or set the back delay."
			::= { link3OBP 14 }

--  1.3.6.1.4.1.47477.10.21.3.3.15
		-- 1.3.6.1.4.1.47477.10.21.3.3.15
		link3_ActiveHeartSwitch OBJECT-TYPE
			SYNTAX INTEGER
				{
				off(0),
				on(1)
				}
			MAX-ACCESS read-write
			STATUS current
			DESCRIPTION
				"get or set the switch status of active heartbeat."
			::= { link3OBP 15 }

		
--  1.3.6.1.4.1.47477.10.21.3.3.16
		-- 1.3.6.1.4.1.47477.10.21.3.3.16
		link3_ActiveSendInterval OBJECT-TYPE
			SYNTAX Integer32
			MAX-ACCESS read-write
			STATUS current
			DESCRIPTION
				"get or set the send interval of active heartbeat."
			::= { link3OBP 16 }		

--  1.3.6.1.4.1.47477.10.21.3.3.17
		-- 1.3.6.1.4.1.47477.10.21.3.3.17
		link3_ActiveTimeOut OBJECT-TYPE
			SYNTAX Integer32
			MAX-ACCESS read-write
			STATUS current
			DESCRIPTION
				"get or set how long the active heartbeat send timeout."
			::= { link3OBP 17 }

--  1.3.6.1.4.1.47477.10.21.3.3.18
		-- 1.3.6.1.4.1.47477.10.21.3.3.18
		link3_ActiveLossBypass OBJECT-TYPE
			SYNTAX Integer32
			MAX-ACCESS read-write
			STATUS current
			DESCRIPTION
				"get or set the bypass for active heartbeat packet loss."
			::= { link3OBP 18 }

--  1.3.6.1.4.1.47477.10.21.3.3.19
		-- 1.3.6.1.4.1.47477.10.21.3.3.19
		link3_PingIpAddress OBJECT-TYPE
			SYNTAX IpAddress
			MAX-ACCESS read-write
			STATUS current
			DESCRIPTION
				"get or set the ping ip address of link3."
			::= { link3OBP 19 }

--  1.3.6.1.4.1.47477.10.21.3.3.20
		-- 1.3.6.1.4.1.47477.10.21.3.3.20
		link3_PassiveHeartSwitch OBJECT-TYPE
			SYNTAX INTEGER
				{
				off(0),
				on(1)
				}
			MAX-ACCESS read-write
			STATUS current
			DESCRIPTION
				"get or set the switch status of passive heartbeat."
			::= { link3OBP 20 }
	

--  1.3.6.1.4.1.47477.10.21.3.3.21
		-- 1.3.6.1.4.1.47477.10.21.3.3.21
		link3_PassiveTimeOut OBJECT-TYPE
			SYNTAX Integer32
			MAX-ACCESS read-write
			STATUS current
			DESCRIPTION
				"get or set how long the passive heartbeat send timeout."
			::= { link3OBP 21 }

--  1.3.6.1.4.1.47477.10.21.3.3.22
		-- 1.3.6.1.4.1.47477.10.21.3.3.22
		link3_PassiveLossBypass OBJECT-TYPE
			SYNTAX Integer32
			MAX-ACCESS read-write
			STATUS current
			DESCRIPTION
				"get or set the bypass for passive heartbeat packet loss."
			::= { link3OBP 22 }

--  1.3.6.1.4.1.47477.10.21.3.3.23
		-- 1.3.6.1.4.1.47477.10.21.3.3.23
		link3_SwitchProtect OBJECT-TYPE
			SYNTAX INTEGER
				{
				off(0),
				on(1)
				}
			MAX-ACCESS read-write
			STATUS current
			DESCRIPTION
				"get or set the switch protection status of link3."
			::= { link3OBP 23 }
			
--  1.3.6.1.4.1.47477.10.21.3.3.24
		-- 1.3.6.1.4.1.47477.10.21.3.3.24
		link3_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link3OBP 24 }		

--  1.3.6.1.4.1.47477.10.21.3.3.25
		-- 1.3.6.1.4.1.47477.10.21.3.3.25
		link3_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link3OBP 25 }	

--  1.3.6.1.4.1.47477.10.21.3.3.26
		-- 1.3.6.1.4.1.47477.10.21.3.3.26
		link3_PowerAlarmStatus OBJECT-TYPE
			SYNTAX INTEGER
				{
				off(0),
				alarm(1),
				normal(2),
				na(3)
				}
			MAX-ACCESS read-only
			STATUS current
			DESCRIPTION
				"get whether a power alarm is generated."
			::= { link3OBP 26 }	


-- 1.3.6.1.4.1.47477.10.21.3.3.50.1
	link3_WorkModeChange 	OBJECT-TYPE    
    SYNTAX INTEGER	{
				manualMode(0),
				autoMode(1)
		}
	MAX-ACCESS read-only
	STATUS current
    DESCRIPTION
        "The Link mode Changed."
    ::= {link3OBPTrap 1}

-- 1.3.6.1.4.1.47477.10.21.3.3.50.2
	link3_StateChange 	OBJECT-TYPE    
    SYNTAX INTEGER	{
				bypass(0),
				primary(1)
		}
	MAX-ACCESS read-only
	STATUS current
    DESCRIPTION
        "The Link State(Channel) Changed."
    ::= {link3OBPTrap 2}

-- 1.3.6.1.4.1.47477.10.21.3.3.50.3
	link3_R1WaveSet 	OBJECT-TYPE    
    SYNTAX INTEGER	{
				w1310nm(0),
				w1550nm(1)
		}
	MAX-ACCESS read-only
	STATUS current
    DESCRIPTION
        "Set The link3 R1 Wave."
    ::= {link3OBPTrap 3}

-- 1.3.6.1.4.1.47477.10.21.3.3.50.4
	link3_R2WaveSet 	OBJECT-TYPE    
    SYNTAX INTEGER	{
				w1310nm(0),
				w1550nm(1)
		}
	MAX-ACCESS read-only
	STATUS current
    DESCRIPTION
        "Set The link3 R2 Wave."
    ::= {link3OBPTrap 4}			

-- 1.3.6.1.4.1.47477.10.21.3.3.50.5
	link3_R3WaveSet 	OBJECT-TYPE    
    SYNTAX INTEGER	{
				w1310nm(0),
				w1550nm(1)
		}
	MAX-ACCESS read-only
	STATUS current
    DESCRIPTION
        "Set The link3 R3 Wave."
    ::= {link3OBPTrap 5}

-- 1.3.6.1.4.1.47477.10.21.3.3.50.6
	link3_R4WaveSet 	OBJECT-TYPE    
    SYNTAX INTEGER	{
				w1310nm(0),
				w1550nm(1)
		}
	MAX-ACCESS read-only
	STATUS current
    DESCRIPTION
        "Set The link3 R4 Wave."
    ::= {link3OBPTrap 6}	
	
-- 1.3.6.1.4.1.47477.10.21.3.3.50.7
	link3_R1AlarmSet 	OBJECT-TYPE    
    SYNTAX DisplayString
	MAX-ACCESS read-only
	STATUS current
    DESCRIPTION
        "Set The link3 R1 Alarm Threshold."
    ::= {link3OBPTrap 7}

-- 1.3.6.1.4.1.47477.10.21.3.3.50.8
	link3_R2AlarmSet 	OBJECT-TYPE    
    SYNTAX DisplayString
	MAX-ACCESS read-only
	STATUS current
    DESCRIPTION
        "Set The link3 R2 Alarm Threshold."
    ::= {link3OBPTrap 8}
	
-- 1.3.6.1.4.1.47477.10.21.3.3.50.9
	link3_R3AlarmSet 	OBJECT-TYPE    
    SYNTAX DisplayString
	MAX-ACCESS read-only
	STATUS current
    DESCRIPTION
        "Set The link3 R3 Alarm Threshold."
    ::= {link3OBPTrap 9}

-- 1.3.6.1.4.1.47477.10.21.3.3.50.10
	link3_R4AlarmSet 	OBJECT-TYPE    
    SYNTAX DisplayString
	MAX-ACCESS read-only
	STATUS current
    DESCRIPTION
        "Set The link3 R4 Alarm Threshold."
    ::= {link3OBPTrap 10}	
	
	
-- 1.3.6.1.4.1.47477.10.21.3.3.50.11
	link3_1R1AlarmSet 	OBJECT-TYPE    
    SYNTAX DisplayString
	MAX-ACCESS read-only
	STATUS current
    DESCRIPTION
        "Set The link3 1R1 Alarm Threshold."
    ::= {link3OBPTrap 11}

-- 1.3.6.1.4.1.47477.10.21.3.3.50.12
	link3_2R1AlarmSet 	OBJECT-TYPE    
    SYNTAX DisplayString
	MAX-ACCESS read-only
	STATUS current
    DESCRIPTION
        "Set The link3 2R1 Alarm Threshold."
    ::= {link3OBPTrap 12}
	
-- 1.3.6.1.4.1.47477.10.21.3.3.50.13
	link3_1R2AlarmSet 	OBJECT-TYPE    
    SYNTAX DisplayString
	MAX-ACCESS read-only
	STATUS current
    DESCRIPTION
        "Set The link3 1R2 Alarm Threshold."
    ::= {link3OBPTrap 13}

-- 1.3.6.1.4.1.47477.10.21.3.3.50.14
	link3_2R2AlarmSet 	OBJECT-TYPE    
    SYNTAX DisplayString
	MAX-ACCESS read-only
	STATUS current
    DESCRIPTION
        "Set The link3 2R2 Alarm Threshold."
    ::= {link3OBPTrap 14}
	
-- 1.3.6.1.4.1.47477.10.21.3.3.50.15
	link3_1R3AlarmSet 	OBJECT-TYPE    
    SYNTAX DisplayString
	MAX-ACCESS read-only
	STATUS current
    DESCRIPTION
        "Set The link3 1R3 Alarm Threshold."
    ::= {link3OBPTrap 15}

-- 1.3.6.1.4.1.47477.10.21.3.3.50.16
	link3_2R3AlarmSet 	OBJECT-TYPE    
    SYNTAX DisplayString
	MAX-ACCESS read-only
	STATUS current
    DESCRIPTION
        "Set The link3 2R3 Alarm Threshold."
    ::= {link3OBPTrap 16}
	
-- 1.3.6.1.4.1.47477.10.21.3.3.50.17
	link3_1R4AlarmSet 	OBJECT-TYPE    
    SYNTAX DisplayString
	MAX-ACCESS read-only
	STATUS current
    DESCRIPTION
        "Set The link3 1R4 Alarm Threshold."
    ::= {link3OBPTrap 17}

-- 1.3.6.1.4.1.47477.10.21.3.3.50.18
	link3_2R4AlarmSet 	OBJECT-TYPE    
    SYNTAX DisplayString
	MAX-ACCESS read-only
	STATUS current
    DESCRIPTION
        "Set The link3 2R4 Alarm Threshold."
    ::= {link3OBPTrap 18}
	
-- 1.3.6.1.4.1.47477.10.21.3.3.50.19
	link3_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link3 PowerAlarmBypass2 Changed."
    ::= {link3OBPTrap 19}
	
-- 1.3.6.1.4.1.47477.10.21.3.3.50.20
	link3_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link3 PowerAlarmBypass4 Changed."
    ::= {link3OBPTrap 20}	
	
-- 1.3.6.1.4.1.47477.10.21.3.3.50.21
	link3_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link3 PowerAlarmBypass8 Changed."
    ::= {link3OBPTrap 21}
	
-- 1.3.6.1.4.1.47477.10.21.3.3.50.22
	link3_powerAlarmR1 	OBJECT-TYPE    
    SYNTAX DisplayString
	MAX-ACCESS read-only
	STATUS current
    DESCRIPTION
        "Set The link3 R1 Power Status Alarm."
    ::= {link3OBPTrap 22}
	
-- 1.3.6.1.4.1.47477.10.21.3.3.50.23
	link3_powerAlarmR2 	OBJECT-TYPE    
    SYNTAX DisplayString
	MAX-ACCESS read-only
	STATUS current
    DESCRIPTION
        "Set The link3 R2 Power Status Alarm."
    ::= {link3OBPTrap 23}
	
-- 1.3.6.1.4.1.47477.10.21.3.3.50.24
	link3_powerAlarmR3 	OBJECT-TYPE    
    SYNTAX DisplayString
	MAX-ACCESS read-only
	STATUS current
    DESCRIPTION
        "Set The link3 R3 Power Status Alarm."
    ::= {link3OBPTrap 24}
	
-- 1.3.6.1.4.1.47477.10.21.3.3.50.25
	link3_powerAlarmR4 	OBJECT-TYPE    
    SYNTAX DisplayString
	MAX-ACCESS read-only
	STATUS current
    DESCRIPTION
        "Set The link3 R4 Power Status Alarm."
    ::= {link3OBPTrap 25}
	
	
-- 1.3.6.1.4.1.47477.10.21.3.3.50.26
	link3_powerAlarm1R1 	OBJECT-TYPE    
    SYNTAX DisplayString
	MAX-ACCESS read-only
	STATUS current
    DESCRIPTION
        "Set The link3 1R1 Power Status Alarm."
    ::= {link3OBPTrap 26}
	
-- 1.3.6.1.4.1.47477.10.21.3.3.50.27
	link3_powerAlarm2R1 	OBJECT-TYPE    
    SYNTAX DisplayString
	MAX-ACCESS read-only
	STATUS current
    DESCRIPTION
        "Set The link3 2R1 Power Status Alarm."
    ::= {link3OBPTrap 27}
	
-- 1.3.6.1.4.1.47477.10.21.3.3.50.28
	link3_powerAlarm1R2 	OBJECT-TYPE    
    SYNTAX DisplayString
	MAX-ACCESS read-only
	STATUS current
    DESCRIPTION
        "Set The link3 1R2 Power Status Alarm."
    ::= {link3OBPTrap 28}
	
-- 1.3.6.1.4.1.47477.10.21.3.3.50.29
	link3_powerAlarm2R2 	OBJECT-TYPE    
    SYNTAX DisplayString
	MAX-ACCESS read-only
	STATUS current
    DESCRIPTION
        "Set The link3 2R2 Power Status Alarm."
    ::= {link3OBPTrap 29}
	
-- 1.3.6.1.4.1.47477.10.21.3.3.50.30
	link3_powerAlarm1R3 	OBJECT-TYPE    
    SYNTAX DisplayString
	MAX-ACCESS read-only
	STATUS current
    DESCRIPTION
        "Set The link3 1R3 Power Status Alarm."
    ::= {link3OBPTrap 30}
	
-- 1.3.6.1.4.1.47477.10.21.3.3.50.31
	link3_powerAlarm2R3 	OBJECT-TYPE    
    SYNTAX DisplayString
	MAX-ACCESS read-only
	STATUS current
    DESCRIPTION
        "Set The link3 2R1 Power Status Alarm."
    ::= {link3OBPTrap 31}
	
-- 1.3.6.1.4.1.47477.10.21.3.3.50.32
	link3_powerAlarm1R4 	OBJECT-TYPE    
    SYNTAX DisplayString
	MAX-ACCESS read-only
	STATUS current
    DESCRIPTION
        "Set The link3 1R4 Power Status Alarm."
    ::= {link3OBPTrap 32}
	
-- 1.3.6.1.4.1.47477.10.21.3.3.50.33
	link3_powerAlarm2R4 	OBJECT-TYPE    
    SYNTAX DisplayString
	MAX-ACCESS read-only
	STATUS current
    DESCRIPTION
        "Set The link3 2R4 Power Status Alarm."
    ::= {link3OBPTrap 33}
	
--  1.3.6.1.4.1.47477.10.21.4.3.1
		-- 1.3.6.1.4.1.47477.10.21.4.3.1
		link4_State OBJECT-TYPE
			SYNTAX INTEGER
				{
				off(0),
				on(1)
				}
			MAX-ACCESS read-only
			STATUS current
			DESCRIPTION
				"get the information about whether link4 is working."
			::= { link4OBP 1 }

		
--  1.3.6.1.4.1.47477.10.21.4.3.2
		-- 1.3.6.1.4.1.47477.10.21.4.3.2
		link4_DeviceType OBJECT-TYPE
			SYNTAX DisplayString
			MAX-ACCESS read-only
			STATUS current
			DESCRIPTION
				"get the type of card in link4."
			::= { link4OBP 2 }

			
--  1.3.6.1.4.1.47477.10.21.4.3.3
		-- 1.3.6.1.4.1.47477.10.21.4.3.3
		link4_WorkMode OBJECT-TYPE
			SYNTAX INTEGER
				{
				manualMode(0),
				autoMode(1)
				}
			MAX-ACCESS read-write
			STATUS current
			DESCRIPTION
				"get or set link4's work mode."
			::= { link4OBP 3 }

		
--  1.3.6.1.4.1.47477.10.21.4.3.4
		-- 1.3.6.1.4.1.47477.10.21.4.3.4
		link4_Channel OBJECT-TYPE
			SYNTAX INTEGER
				{
				bypass(0),
				primary(1)
				}
			MAX-ACCESS read-write
			STATUS current
			DESCRIPTION
				"get or set the channel in which link4 works."
			::= { link4OBP 4 }


--  1.3.6.1.4.1.47477.10.21.4.3.5
		-- 1.3.6.1.4.1.47477.10.21.4.3.5
		link4_R1Power OBJECT-TYPE
			SYNTAX DisplayString
			MAX-ACCESS read-only
			STATUS current
			DESCRIPTION
				"get the power of R1 in link4."
			::= { link4OBP 5 }

		
--  1.3.6.1.4.1.47477.10.21.4.3.6
		-- 1.3.6.1.4.1.47477.10.21.4.3.6
		link4_R2Power OBJECT-TYPE
			SYNTAX DisplayString
			MAX-ACCESS read-only
			STATUS current
			DESCRIPTION
				"get the power of R2 in link4."
			::= { link4OBP 6 }
			
--  1.3.6.1.4.1.47477.10.21.4.3.35
		-- 1.3.6.1.4.1.47477.10.21.4.3.35
		link4_R3Power OBJECT-TYPE
			SYNTAX DisplayString
			MAX-ACCESS read-only
			STATUS current
			DESCRIPTION
				"get the power of R3 in link4."
			::= { link4OBP 35 }
			
--  1.3.6.1.4.1.47477.10.21.4.3.36
		-- 1.3.6.1.4.1.47477.10.21.4.3.36
		link4_R4Power OBJECT-TYPE
			SYNTAX DisplayString
			MAX-ACCESS read-only
			STATUS current
			DESCRIPTION
				"get the power of R4 in link4."
			::= { link4OBP 36 }		
		
--  1.3.6.1.4.1.47477.10.21.4.3.7
		-- 1.3.6.1.4.1.47477.10.21.4.3.7
		link4_R1Wave OBJECT-TYPE
			SYNTAX INTEGER
				{
				w1310nm(0),
				w1550nm(1),
				na(2)
				}
			MAX-ACCESS read-write
			STATUS current
			DESCRIPTION
				"get or set the wave length of R1 in link4."
			::= { link4OBP 7 }

		
--  1.3.6.1.4.1.47477.10.21.4.3.8
		-- 1.3.6.1.4.1.47477.10.21.4.3.8
		link4_R2Wave OBJECT-TYPE
			SYNTAX INTEGER
				{
				w1310nm(0),
				w1550nm(1),
				na(2)
				}
			MAX-ACCESS read-write
			STATUS current
			DESCRIPTION
				"get or set the wave length of R2 in link4."
			::= { link4OBP 8 }


--  1.3.6.1.4.1.47477.10.21.4.3.27
		-- 1.3.6.1.4.1.47477.10.21.4.3.27
		link4_R3Wave OBJECT-TYPE
			SYNTAX INTEGER
				{
				w1310nm(0),
				w1550nm(1),
				na(2)
				}
			MAX-ACCESS read-write
			STATUS current
			DESCRIPTION
				"get or set the wave length of R3 in link4."
			::= { link4OBP 27 }

		
--  1.3.6.1.4.1.47477.10.21.4.3.28
		-- 1.3.6.1.4.1.47477.10.21.4.3.28
		link4_R4Wave OBJECT-TYPE
			SYNTAX INTEGER
				{
				w1310nm(0),
				w1550nm(1),
				na(2)
				}
			MAX-ACCESS read-write
			STATUS current
			DESCRIPTION
				"get or set the wave length of R4 in link4."
			::= { link4OBP 28 }
			
--  1.3.6.1.4.1.47477.10.21.4.3.9
		-- 1.3.6.1.4.1.47477.10.21.4.3.9
		link4_R1AlarmPower OBJECT-TYPE
			SYNTAX DisplayString
			MAX-ACCESS read-write
			STATUS current
			DESCRIPTION
				"get or set the power alarm threshold of R1 in link4."
			::= { link4OBP 9 }

		
--  1.3.6.1.4.1.47477.10.21.4.3.10
		-- 1.3.6.1.4.1.47477.10.21.4.3.10
		link4_R2AlarmPower OBJECT-TYPE
			SYNTAX DisplayString
			MAX-ACCESS read-write
			STATUS current
			DESCRIPTION
				"get or set the power alarm threshold of R2 in link4."
			::= { link4OBP 10 }


--  1.3.6.1.4.1.47477.10.21.4.3.29
		-- 1.3.6.1.4.1.47477.10.21.4.3.29
		link4_R3AlarmPower OBJECT-TYPE
			SYNTAX DisplayString
			MAX-ACCESS read-write
			STATUS current
			DESCRIPTION
				"get or set the power alarm threshold of R3 in link4."
			::= { link4OBP 29 }

		
--  1.3.6.1.4.1.47477.10.21.4.3.30
		-- 1.3.6.1.4.1.47477.10.21.4.3.30
		link4_R4AlarmPower OBJECT-TYPE
			SYNTAX DisplayString
			MAX-ACCESS read-write
			STATUS current
			DESCRIPTION
				"get or set the power alarm threshold of R4 in link4."
			::= { link4OBP 30 }

-- OBP4
--  1.3.6.1.4.1.47477.10.21.4.3.37
		-- 1.3.6.1.4.1.47477.10.21.4.3.37
		link4_1R1Power OBJECT-TYPE
			SYNTAX DisplayString
			MAX-ACCESS read-only
			STATUS current
			DESCRIPTION
				"get the power of 1R1 in link4."
			::= { link4OBP 37 }
			
--  1.3.6.1.4.1.47477.10.21.4.3.38
		-- 1.3.6.1.4.1.47477.10.21.4.3.38
		link4_1R2Power OBJECT-TYPE
			SYNTAX DisplayString
			MAX-ACCESS read-only
			STATUS current
			DESCRIPTION
				"get the power of 1R2 in link4."
			::= { link4OBP 38 }

--  1.3.6.1.4.1.47477.10.21.4.3.39
		-- 1.3.6.1.4.1.47477.10.21.4.3.39
		link4_1R3Power OBJECT-TYPE
			SYNTAX DisplayString
			MAX-ACCESS read-only
			STATUS current
			DESCRIPTION
				"get the power of 1R3 in link4."
			::= { link4OBP 39 }
			
--  1.3.6.1.4.1.47477.10.21.4.3.40
		-- 1.3.6.1.4.1.47477.10.21.4.3.40
		link4_1R4Power OBJECT-TYPE
			SYNTAX DisplayString
			MAX-ACCESS read-only
			STATUS current
			DESCRIPTION
				"get the power of 1R4 in link4."
			::= { link4OBP 40 }

--  1.3.6.1.4.1.47477.10.21.4.3.41
		-- 1.3.6.1.4.1.47477.10.21.4.3.41
		link4_2R1Power OBJECT-TYPE
			SYNTAX DisplayString
			MAX-ACCESS read-only
			STATUS current
			DESCRIPTION
				"get the power of 2R1 in link4."
			::= { link4OBP 41 }
			
--  1.3.6.1.4.1.47477.10.21.4.3.42
		-- 1.3.6.1.4.1.47477.10.21.4.3.42
		link4_2R2Power OBJECT-TYPE
			SYNTAX DisplayString
			MAX-ACCESS read-only
			STATUS current
			DESCRIPTION
				"get the power of 2R2 in link4."
			::= { link4OBP 42 }

--  1.3.6.1.4.1.47477.10.21.4.3.41
		-- 1.3.6.1.4.1.47477.10.21.4.3.43
		link4_2R3Power OBJECT-TYPE
			SYNTAX DisplayString
			MAX-ACCESS read-only
			STATUS current
			DESCRIPTION
				"get the power of 2R3 in link4."
			::= { link4OBP 43 }
			
--  1.3.6.1.4.1.47477.10.21.4.3.42
		-- 1.3.6.1.4.1.47477.10.21.4.3.44
		link4_2R4Power OBJECT-TYPE
			SYNTAX DisplayString
			MAX-ACCESS read-only
			STATUS current
			DESCRIPTION
				"get the power of 2R4 in link4."
			::= { link4OBP 44 }
			
--  1.3.6.1.4.1.47477.10.21.4.3.49
		-- 1.3.6.1.4.1.47477.10.21.4.3.49
		link4_1R1Wave OBJECT-TYPE
			SYNTAX INTEGER
				{
				w850nm(0),
				na(2)
				}
			MAX-ACCESS read-only
			STATUS current
			DESCRIPTION
				"get the wave length of 1R1 in link4."
			::= { link4OBP 49 }
		
--  1.3.6.1.4.1.47477.10.21.4.3.60
		-- 1.3.6.1.4.1.47477.10.21.4.3.60
		link4_1R2Wave OBJECT-TYPE
			SYNTAX INTEGER
				{
				w850nm(0),
				na(2)
				}
			MAX-ACCESS read-only
			STATUS current
			DESCRIPTION
				"get the wave length of 1R2 in link4."
			::= { link4OBP 60 }

--  1.3.6.1.4.1.47477.10.21.4.3.61
		-- 1.3.6.1.4.1.47477.10.21.4.3.61
		link4_1R3Wave OBJECT-TYPE
			SYNTAX INTEGER
				{
				w850nm(0),
				na(2)
				}
			MAX-ACCESS read-only
			STATUS current
			DESCRIPTION
				"get the wave length of 1R3 in link4."
			::= { link4OBP 61 }

		
--  1.3.6.1.4.1.47477.10.21.4.3.62
		-- 1.3.6.1.4.1.47477.10.21.4.3.62
		link4_1R4Wave OBJECT-TYPE
			SYNTAX INTEGER
				{
				w850nm(0),
				na(2)
				}
			MAX-ACCESS read-only
			STATUS current
			DESCRIPTION
				"get the wave length of 1R4 in link4."
			::= { link4OBP 62 }
	
--  1.3.6.1.4.1.47477.10.21.4.3.63
		-- 1.3.6.1.4.1.47477.10.21.4.3.63
		link4_2R1Wave OBJECT-TYPE
			SYNTAX INTEGER
				{
				w850nm(0),
				na(2)
				}
			MAX-ACCESS read-only
			STATUS current
			DESCRIPTION
				"get the wave length of 2R1 in link4."
			::= { link4OBP 63 }

		
--  1.3.6.1.4.1.47477.10.21.4.3.64
		-- 1.3.6.1.4.1.47477.10.21.4.3.64
		link4_2R2Wave OBJECT-TYPE
			SYNTAX INTEGER
				{
				w850nm(0),
				na(2)
				}
			MAX-ACCESS read-only
			STATUS current
			DESCRIPTION
				"get the wave length of 2R2 in link4."
			::= { link4OBP 64 }	
	
--  1.3.6.1.4.1.47477.10.21.4.3.65
		-- 1.3.6.1.4.1.47477.10.21.4.3.65
		link4_2R3Wave OBJECT-TYPE
			SYNTAX INTEGER
				{
				w850nm(0),
				na(2)
				}
			MAX-ACCESS read-only
			STATUS current
			DESCRIPTION
				"get the wave length of 2R3 in link4."
			::= { link4OBP 65 }

		
--  1.3.6.1.4.1.47477.10.21.4.3.66
		-- 1.3.6.1.4.1.47477.10.21.4.3.66
		link4_2R4Wave OBJECT-TYPE
			SYNTAX INTEGER
				{
				w850nm(0),
				na(2)
				}
			MAX-ACCESS read-only
			STATUS current
			DESCRIPTION
				"get the wave length of 2R4 in link4."
			::= { link4OBP 66 }	
			
--  1.3.6.1.4.1.47477.10.21.4.3.31
		-- 1.3.6.1.4.1.47477.10.21.4.3.31
		link4_1R1AlarmPower OBJECT-TYPE
			SYNTAX DisplayString
			MAX-ACCESS read-write
			STATUS current
			DESCRIPTION
				"get or set the power alarm threshold of 1R1 in link4."
			::= { link4OBP 31 }
			
--  1.3.6.1.4.1.47477.10.21.4.3.32
		-- 1.3.6.1.4.1.47477.10.21.4.3.32
		link4_1R2AlarmPower OBJECT-TYPE
			SYNTAX DisplayString
			MAX-ACCESS read-write
			STATUS current
			DESCRIPTION
				"get or set the power alarm threshold of 1R2 in link4."
			::= { link4OBP 32 }

--  1.3.6.1.4.1.47477.10.21.4.3.33
		-- 1.3.6.1.4.1.47477.10.21.4.3.33
		link4_1R3AlarmPower OBJECT-TYPE
			SYNTAX DisplayString
			MAX-ACCESS read-write
			STATUS current
			DESCRIPTION
				"get or set the power alarm threshold of 1R3 in link4."
			::= { link4OBP 33 }
			
--  1.3.6.1.4.1.47477.10.21.4.3.34
		-- 1.3.6.1.4.1.47477.10.21.4.3.34
		link4_1R4AlarmPower OBJECT-TYPE
			SYNTAX DisplayString
			MAX-ACCESS read-write
			STATUS current
			DESCRIPTION
				"get or set the power alarm threshold of 1R4 in link4."
			::= { link4OBP 34 }

--  1.3.6.1.4.1.47477.10.21.4.3.45
		-- 1.3.6.1.4.1.47477.10.21.4.3.45
		link4_2R1AlarmPower OBJECT-TYPE
			SYNTAX DisplayString
			MAX-ACCESS read-write
			STATUS current
			DESCRIPTION
				"get or set the power alarm threshold of 2R1 in link4."
			::= { link4OBP 45 }
			
--  1.3.6.1.4.1.47477.10.21.4.3.46
		-- 1.3.6.1.4.1.47477.10.21.4.3.46
		link4_2R2AlarmPower OBJECT-TYPE
			SYNTAX DisplayString
			MAX-ACCESS read-write
			STATUS current
			DESCRIPTION
				"get or set the power alarm threshold of 2R2 in link4."
			::= { link4OBP 46 }

--  1.3.6.1.4.1.47477.10.21.4.3.47
		-- 1.3.6.1.4.1.47477.10.21.4.3.47
		link4_2R3AlarmPower OBJECT-TYPE
			SYNTAX DisplayString
			MAX-ACCESS read-write
			STATUS current
			DESCRIPTION
				"get or set the power alarm threshold of 2R3 in link4."
			::= { link4OBP 47 }
			
--  1.3.6.1.4.1.47477.10.21.4.3.48
		-- 1.3.6.1.4.1.47477.10.21.4.3.48
		link4_2R4AlarmPower OBJECT-TYPE
			SYNTAX DisplayString
			MAX-ACCESS read-write
			STATUS current
			DESCRIPTION
				"get or set the power alarm threshold of 2R4 in link4."
			::= { link4OBP 48 }
			
--  1.3.6.1.4.1.47477.10.21.4.3.11
		-- 1.3.6.1.4.1.47477.10.21.4.3.11
		link4_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link4OBP 11 }
			
--  1.3.6.1.4.1.47477.10.21.4.3.67
		-- 1.3.6.1.4.1.47477.10.21.4.3.67
		link4_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link4OBP 67 }
			
--  1.3.6.1.4.1.47477.10.21.4.3.68
		-- 1.3.6.1.4.1.47477.10.21.4.3.68
		link4_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link4OBP 68 }
			
--  1.3.6.1.4.1.47477.10.21.4.3.12
		-- 1.3.6.1.4.1.47477.10.21.4.3.12
		link4_ReturnDelay OBJECT-TYPE
			--SYNTAX Integer32
			SYNTAX Integer32
			MAX-ACCESS read-write
			STATUS current
			DESCRIPTION
				"get or set how long link4 takes to return to automatic mode."
			::= { link4OBP 12 }
			
--  1.3.6.1.4.1.47477.10.21.4.3.13
		-- 1.3.6.1.4.1.47477.10.21.4.3.13
		link4_BackMode OBJECT-TYPE
			SYNTAX INTEGER
				{
				autoNoBack(0),
				autoBack(1)
				}
			MAX-ACCESS read-write
			STATUS current
			DESCRIPTION
				"get or set the back mode of link4."
			::= { link4OBP 13 }

		
--  1.3.6.1.4.1.47477.10.21.4.3.14
		-- 1.3.6.1.4.1.47477.10.21.4.3.14
		link4_BackDelay OBJECT-TYPE
			SYNTAX Integer32
			MAX-ACCESS read-write
			STATUS current
			DESCRIPTION
				"get or set the back delay."
			::= { link4OBP 14 }

--  1.3.6.1.4.1.47477.10.21.4.3.15
		-- 1.3.6.1.4.1.47477.10.21.4.3.15
		link4_ActiveHeartSwitch OBJECT-TYPE
			SYNTAX INTEGER
				{
				off(0),
				on(1)
				}
			MAX-ACCESS read-write
			STATUS current
			DESCRIPTION
				"get or set the switch status of active heartbeat."
			::= { link4OBP 15 }

		
--  1.3.6.1.4.1.47477.10.21.4.3.16
		-- 1.3.6.1.4.1.47477.10.21.4.3.16
		link4_ActiveSendInterval OBJECT-TYPE
			SYNTAX Integer32
			MAX-ACCESS read-write
			STATUS current
			DESCRIPTION
				"get or set the send interval of active heartbeat."
			::= { link4OBP 16 }		

--  1.3.6.1.4.1.47477.10.21.4.3.17
		-- 1.3.6.1.4.1.47477.10.21.4.3.17
		link4_ActiveTimeOut OBJECT-TYPE
			SYNTAX Integer32
			MAX-ACCESS read-write
			STATUS current
			DESCRIPTION
				"get or set how long the active heartbeat send timeout."
			::= { link4OBP 17 }

--  1.3.6.1.4.1.47477.10.21.4.3.18
		-- 1.3.6.1.4.1.47477.10.21.4.3.18
		link4_ActiveLossBypass OBJECT-TYPE
			SYNTAX Integer32
			MAX-ACCESS read-write
			STATUS current
			DESCRIPTION
				"get or set the bypass for active heartbeat packet loss."
			::= { link4OBP 18 }

--  1.3.6.1.4.1.47477.10.21.4.3.19
		-- 1.3.6.1.4.1.47477.10.21.4.3.19
		link4_PingIpAddress OBJECT-TYPE
			SYNTAX IpAddress
			MAX-ACCESS read-write
			STATUS current
			DESCRIPTION
				"get or set the ping ip address of link4."
			::= { link4OBP 19 }

--  1.3.6.1.4.1.47477.10.21.4.3.20
		-- 1.3.6.1.4.1.47477.10.21.4.3.20
		link4_PassiveHeartSwitch OBJECT-TYPE
			SYNTAX INTEGER
				{
				off(0),
				on(1)
				}
			MAX-ACCESS read-write
			STATUS current
			DESCRIPTION
				"get or set the switch status of passive heartbeat."
			::= { link4OBP 20 }
	

--  1.3.6.1.4.1.47477.10.21.4.3.21
		-- 1.3.6.1.4.1.47477.10.21.4.3.21
		link4_PassiveTimeOut OBJECT-TYPE
			SYNTAX Integer32
			MAX-ACCESS read-write
			STATUS current
			DESCRIPTION
				"get or set how long the passive heartbeat send timeout."
			::= { link4OBP 21 }

--  1.3.6.1.4.1.47477.10.21.4.3.22
		-- 1.3.6.1.4.1.47477.10.21.4.3.22
		link4_PassiveLossBypass OBJECT-TYPE
			SYNTAX Integer32
			MAX-ACCESS read-write
			STATUS current
			DESCRIPTION
				"get or set the bypass for passive heartbeat packet loss."
			::= { link4OBP 22 }

--  1.3.6.1.4.1.47477.10.21.4.3.23
		-- 1.3.6.1.4.1.47477.10.21.4.3.23
		link4_SwitchProtect OBJECT-TYPE
			SYNTAX INTEGER
				{
				off(0),
				on(1)
				}
			MAX-ACCESS read-write
			STATUS current
			DESCRIPTION
				"get or set the switch protection status of link4."
			::= { link4OBP 23 }
			
--  1.3.6.1.4.1.47477.10.21.4.3.24
		-- 1.3.6.1.4.1.47477.10.21.4.3.24
		link4_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link4OBP 24 }		

--  1.3.6.1.4.1.47477.10.21.4.3.25
		-- 1.3.6.1.4.1.47477.10.21.4.3.25
		link4_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link4OBP 25 }	

--  1.3.6.1.4.1.47477.10.21.4.3.26
		-- 1.3.6.1.4.1.47477.10.21.4.3.26
		link4_PowerAlarmStatus OBJECT-TYPE
			SYNTAX INTEGER
				{
				off(0),
				alarm(1),
				normal(2),
				na(3)
				}
			MAX-ACCESS read-only
			STATUS current
			DESCRIPTION
				"get whether a power alarm is generated."
			::= { link4OBP 26 }	


-- 1.3.6.1.4.1.47477.10.21.4.3.50.1
	link4_WorkModeChange 	OBJECT-TYPE    
    SYNTAX INTEGER	{
				manualMode(0),
				autoMode(1)
		}
	MAX-ACCESS read-only
	STATUS current
    DESCRIPTION
        "The Link mode Changed."
    ::= {link4OBPTrap 1}

-- 1.3.6.1.4.1.47477.10.21.4.3.50.2
	link4_StateChange 	OBJECT-TYPE    
    SYNTAX INTEGER	{
				bypass(0),
				primary(1)
		}
	MAX-ACCESS read-only
	STATUS current
    DESCRIPTION
        "The Link State(Channel) Changed."
    ::= {link4OBPTrap 2}

-- 1.3.6.1.4.1.47477.10.21.4.3.50.3
	link4_R1WaveSet 	OBJECT-TYPE    
    SYNTAX INTEGER	{
				w1310nm(0),
				w1550nm(1)
		}
	MAX-ACCESS read-only
	STATUS current
    DESCRIPTION
        "Set The link4 R1 Wave."
    ::= {link4OBPTrap 3}

-- 1.3.6.1.4.1.47477.10.21.4.3.50.4
	link4_R2WaveSet 	OBJECT-TYPE    
    SYNTAX INTEGER	{
				w1310nm(0),
				w1550nm(1)
		}
	MAX-ACCESS read-only
	STATUS current
    DESCRIPTION
        "Set The link4 R2 Wave."
    ::= {link4OBPTrap 4}			

-- 1.3.6.1.4.1.47477.10.21.4.3.50.5
	link4_R3WaveSet 	OBJECT-TYPE    
    SYNTAX INTEGER	{
				w1310nm(0),
				w1550nm(1)
		}
	MAX-ACCESS read-only
	STATUS current
    DESCRIPTION
        "Set The link4 R3 Wave."
    ::= {link4OBPTrap 5}

-- 1.3.6.1.4.1.47477.10.21.4.3.50.6
	link4_R4WaveSet 	OBJECT-TYPE    
    SYNTAX INTEGER	{
				w1310nm(0),
				w1550nm(1)
		}
	MAX-ACCESS read-only
	STATUS current
    DESCRIPTION
        "Set The link4 R4 Wave."
    ::= {link4OBPTrap 6}	
	
-- 1.3.6.1.4.1.47477.10.21.4.3.50.7
	link4_R1AlarmSet 	OBJECT-TYPE    
    SYNTAX DisplayString
	MAX-ACCESS read-only
	STATUS current
    DESCRIPTION
        "Set The link4 R1 Alarm Threshold."
    ::= {link4OBPTrap 7}

-- 1.3.6.1.4.1.47477.10.21.4.3.50.8
	link4_R2AlarmSet 	OBJECT-TYPE    
    SYNTAX DisplayString
	MAX-ACCESS read-only
	STATUS current
    DESCRIPTION
        "Set The link4 R2 Alarm Threshold."
    ::= {link4OBPTrap 8}
	
-- 1.3.6.1.4.1.47477.10.21.4.3.50.9
	link4_R3AlarmSet 	OBJECT-TYPE    
    SYNTAX DisplayString
	MAX-ACCESS read-only
	STATUS current
    DESCRIPTION
        "Set The link4 R3 Alarm Threshold."
    ::= {link4OBPTrap 9}

-- 1.3.6.1.4.1.47477.10.21.4.3.50.10
	link4_R4AlarmSet 	OBJECT-TYPE    
    SYNTAX DisplayString
	MAX-ACCESS read-only
	STATUS current
    DESCRIPTION
        "Set The link4 R4 Alarm Threshold."
    ::= {link4OBPTrap 10}	
	
	
-- 1.3.6.1.4.1.47477.10.21.4.3.50.11
	link4_1R1AlarmSet 	OBJECT-TYPE    
    SYNTAX DisplayString
	MAX-ACCESS read-only
	STATUS current
    DESCRIPTION
        "Set The link4 1R1 Alarm Threshold."
    ::= {link4OBPTrap 11}

-- 1.3.6.1.4.1.47477.10.21.4.3.50.12
	link4_2R1AlarmSet 	OBJECT-TYPE    
    SYNTAX DisplayString
	MAX-ACCESS read-only
	STATUS current
    DESCRIPTION
        "Set The link4 2R1 Alarm Threshold."
    ::= {link4OBPTrap 12}
	
-- 1.3.6.1.4.1.47477.10.21.4.3.50.13
	link4_1R2AlarmSet 	OBJECT-TYPE    
    SYNTAX DisplayString
	MAX-ACCESS read-only
	STATUS current
    DESCRIPTION
        "Set The link4 1R2 Alarm Threshold."
    ::= {link4OBPTrap 13}

-- 1.3.6.1.4.1.47477.10.21.4.3.50.14
	link4_2R2AlarmSet 	OBJECT-TYPE    
    SYNTAX DisplayString
	MAX-ACCESS read-only
	STATUS current
    DESCRIPTION
        "Set The link4 2R2 Alarm Threshold."
    ::= {link4OBPTrap 14}
	
-- 1.3.6.1.4.1.47477.10.21.4.3.50.15
	link4_1R3AlarmSet 	OBJECT-TYPE    
    SYNTAX DisplayString
	MAX-ACCESS read-only
	STATUS current
    DESCRIPTION
        "Set The link4 1R3 Alarm Threshold."
    ::= {link4OBPTrap 15}

-- 1.3.6.1.4.1.47477.10.21.4.3.50.16
	link4_2R3AlarmSet 	OBJECT-TYPE    
    SYNTAX DisplayString
	MAX-ACCESS read-only
	STATUS current
    DESCRIPTION
        "Set The link4 2R3 Alarm Threshold."
    ::= {link4OBPTrap 16}
	
-- 1.3.6.1.4.1.47477.10.21.4.3.50.17
	link4_1R4AlarmSet 	OBJECT-TYPE    
    SYNTAX DisplayString
	MAX-ACCESS read-only
	STATUS current
    DESCRIPTION
        "Set The link4 1R4 Alarm Threshold."
    ::= {link4OBPTrap 17}

-- 1.3.6.1.4.1.47477.10.21.4.3.50.18
	link4_2R4AlarmSet 	OBJECT-TYPE    
    SYNTAX DisplayString
	MAX-ACCESS read-only
	STATUS current
    DESCRIPTION
        "Set The link4 2R4 Alarm Threshold."
    ::= {link4OBPTrap 18}
	
-- 1.3.6.1.4.1.47477.10.21.4.3.50.19
	link4_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link4 PowerAlarmBypass2 Changed."
    ::= {link4OBPTrap 19}
	
-- 1.3.6.1.4.1.47477.10.21.4.3.50.20
	link4_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link4 PowerAlarmBypass4 Changed."
    ::= {link4OBPTrap 20}	
	
-- 1.3.6.1.4.1.47477.10.21.4.3.50.21
	link4_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link4 PowerAlarmBypass8 Changed."
    ::= {link4OBPTrap 21}
	
-- 1.3.6.1.4.1.47477.10.21.4.3.50.22
	link4_powerAlarmR1 	OBJECT-TYPE    
    SYNTAX DisplayString
	MAX-ACCESS read-only
	STATUS current
    DESCRIPTION
        "Set The link4 R1 Power Status Alarm."
    ::= {link4OBPTrap 22}
	
-- 1.3.6.1.4.1.47477.10.21.4.3.50.23
	link4_powerAlarmR2 	OBJECT-TYPE    
    SYNTAX DisplayString
	MAX-ACCESS read-only
	STATUS current
    DESCRIPTION
        "Set The link4 R2 Power Status Alarm."
    ::= {link4OBPTrap 23}
	
-- 1.3.6.1.4.1.47477.10.21.4.3.50.24
	link4_powerAlarmR3 	OBJECT-TYPE    
    SYNTAX DisplayString
	MAX-ACCESS read-only
	STATUS current
    DESCRIPTION
        "Set The link4 R3 Power Status Alarm."
    ::= {link4OBPTrap 24}
	
-- 1.3.6.1.4.1.47477.10.21.4.3.50.25
	link4_powerAlarmR4 	OBJECT-TYPE    
    SYNTAX DisplayString
	MAX-ACCESS read-only
	STATUS current
    DESCRIPTION
        "Set The link4 R4 Power Status Alarm."
    ::= {link4OBPTrap 25}
	
	
-- 1.3.6.1.4.1.47477.10.21.4.3.50.26
	link4_powerAlarm1R1 	OBJECT-TYPE    
    SYNTAX DisplayString
	MAX-ACCESS read-only
	STATUS current
    DESCRIPTION
        "Set The link4 1R1 Power Status Alarm."
    ::= {link4OBPTrap 26}
	
-- 1.3.6.1.4.1.47477.10.21.4.3.50.27
	link4_powerAlarm2R1 	OBJECT-TYPE    
    SYNTAX DisplayString
	MAX-ACCESS read-only
	STATUS current
    DESCRIPTION
        "Set The link4 2R1 Power Status Alarm."
    ::= {link4OBPTrap 27}
	
-- 1.3.6.1.4.1.47477.10.21.4.3.50.28
	link4_powerAlarm1R2 	OBJECT-TYPE    
    SYNTAX DisplayString
	MAX-ACCESS read-only
	STATUS current
    DESCRIPTION
        "Set The link4 1R2 Power Status Alarm."
    ::= {link4OBPTrap 28}
	
-- 1.3.6.1.4.1.47477.10.21.4.3.50.29
	link4_powerAlarm2R2 	OBJECT-TYPE    
    SYNTAX DisplayString
	MAX-ACCESS read-only
	STATUS current
    DESCRIPTION
        "Set The link4 2R2 Power Status Alarm."
    ::= {link4OBPTrap 29}
	
-- 1.3.6.1.4.1.47477.10.21.4.3.50.30
	link4_powerAlarm1R3 	OBJECT-TYPE    
    SYNTAX DisplayString
	MAX-ACCESS read-only
	STATUS current
    DESCRIPTION
        "Set The link4 1R3 Power Status Alarm."
    ::= {link4OBPTrap 30}
	
-- 1.3.6.1.4.1.47477.10.21.4.3.50.31
	link4_powerAlarm2R3 	OBJECT-TYPE    
    SYNTAX DisplayString
	MAX-ACCESS read-only
	STATUS current
    DESCRIPTION
        "Set The link4 2R1 Power Status Alarm."
    ::= {link4OBPTrap 31}
	
-- 1.3.6.1.4.1.47477.10.21.4.3.50.32
	link4_powerAlarm1R4 	OBJECT-TYPE    
    SYNTAX DisplayString
	MAX-ACCESS read-only
	STATUS current
    DESCRIPTION
        "Set The link4 1R4 Power Status Alarm."
    ::= {link4OBPTrap 32}
	
-- 1.3.6.1.4.1.47477.10.21.4.3.50.33
	link4_powerAlarm2R4 	OBJECT-TYPE    
    SYNTAX DisplayString
	MAX-ACCESS read-only
	STATUS current
    DESCRIPTION
        "Set The link4 2R4 Power Status Alarm."
    ::= {link4OBPTrap 33}
	
--  1.3.6.1.4.1.47477.10.21.5.3.1
		-- 1.3.6.1.4.1.47477.10.21.5.3.1
		link5_State OBJECT-TYPE
			SYNTAX INTEGER
				{
				off(0),
				on(1)
				}
			MAX-ACCESS read-only
			STATUS current
			DESCRIPTION
				"get the information about whether link5 is working."
			::= { link5OBP 1 }

		
--  1.3.6.1.4.1.47477.10.21.5.3.2
		-- 1.3.6.1.4.1.47477.10.21.5.3.2
		link5_DeviceType OBJECT-TYPE
			SYNTAX DisplayString
			MAX-ACCESS read-only
			STATUS current
			DESCRIPTION
				"get the type of card in link5."
			::= { link5OBP 2 }

			
--  1.3.6.1.4.1.47477.10.21.5.3.3
		-- 1.3.6.1.4.1.47477.10.21.5.3.3
		link5_WorkMode OBJECT-TYPE
			SYNTAX INTEGER
				{
				manualMode(0),
				autoMode(1)
				}
			MAX-ACCESS read-write
			STATUS current
			DESCRIPTION
				"get or set link5's work mode."
			::= { link5OBP 3 }

		
--  1.3.6.1.4.1.47477.10.21.5.3.4
		-- 1.3.6.1.4.1.47477.10.21.5.3.4
		link5_Channel OBJECT-TYPE
			SYNTAX INTEGER
				{
				bypass(0),
				primary(1)
				}
			MAX-ACCESS read-write
			STATUS current
			DESCRIPTION
				"get or set the channel in which link5 works."
			::= { link5OBP 4 }


--  1.3.6.1.4.1.47477.10.21.5.3.5
		-- 1.3.6.1.4.1.47477.10.21.5.3.5
		link5_R1Power OBJECT-TYPE
			SYNTAX DisplayString
			MAX-ACCESS read-only
			STATUS current
			DESCRIPTION
				"get the power of R1 in link5."
			::= { link5OBP 5 }

		
--  1.3.6.1.4.1.47477.10.21.5.3.6
		-- 1.3.6.1.4.1.47477.10.21.5.3.6
		link5_R2Power OBJECT-TYPE
			SYNTAX DisplayString
			MAX-ACCESS read-only
			STATUS current
			DESCRIPTION
				"get the power of R2 in link5."
			::= { link5OBP 6 }
			
--  1.3.6.1.4.1.47477.10.21.5.3.35
		-- 1.3.6.1.4.1.47477.10.21.5.3.35
		link5_R3Power OBJECT-TYPE
			SYNTAX DisplayString
			MAX-ACCESS read-only
			STATUS current
			DESCRIPTION
				"get the power of R3 in link5."
			::= { link5OBP 35 }
			
--  1.3.6.1.4.1.47477.10.21.5.3.36
		-- 1.3.6.1.4.1.47477.10.21.5.3.36
		link5_R4Power OBJECT-TYPE
			SYNTAX DisplayString
			MAX-ACCESS read-only
			STATUS current
			DESCRIPTION
				"get the power of R4 in link5."
			::= { link5OBP 36 }		
		
--  1.3.6.1.4.1.47477.10.21.5.3.7
		-- 1.3.6.1.4.1.47477.10.21.5.3.7
		link5_R1Wave OBJECT-TYPE
			SYNTAX INTEGER
				{
				w1310nm(0),
				w1550nm(1),
				na(2)
				}
			MAX-ACCESS read-write
			STATUS current
			DESCRIPTION
				"get or set the wave length of R1 in link5."
			::= { link5OBP 7 }

		
--  1.3.6.1.4.1.47477.10.21.5.3.8
		-- 1.3.6.1.4.1.47477.10.21.5.3.8
		link5_R2Wave OBJECT-TYPE
			SYNTAX INTEGER
				{
				w1310nm(0),
				w1550nm(1),
				na(2)
				}
			MAX-ACCESS read-write
			STATUS current
			DESCRIPTION
				"get or set the wave length of R2 in link5."
			::= { link5OBP 8 }


--  1.3.6.1.4.1.47477.10.21.5.3.27
		-- 1.3.6.1.4.1.47477.10.21.5.3.27
		link5_R3Wave OBJECT-TYPE
			SYNTAX INTEGER
				{
				w1310nm(0),
				w1550nm(1),
				na(2)
				}
			MAX-ACCESS read-write
			STATUS current
			DESCRIPTION
				"get or set the wave length of R3 in link5."
			::= { link5OBP 27 }

		
--  1.3.6.1.4.1.47477.10.21.5.3.28
		-- 1.3.6.1.4.1.47477.10.21.5.3.28
		link5_R4Wave OBJECT-TYPE
			SYNTAX INTEGER
				{
				w1310nm(0),
				w1550nm(1),
				na(2)
				}
			MAX-ACCESS read-write
			STATUS current
			DESCRIPTION
				"get or set the wave length of R4 in link5."
			::= { link5OBP 28 }
			
--  1.3.6.1.4.1.47477.10.21.5.3.9
		-- 1.3.6.1.4.1.47477.10.21.5.3.9
		link5_R1AlarmPower OBJECT-TYPE
			SYNTAX DisplayString
			MAX-ACCESS read-write
			STATUS current
			DESCRIPTION
				"get or set the power alarm threshold of R1 in link5."
			::= { link5OBP 9 }

		
--  1.3.6.1.4.1.47477.10.21.5.3.10
		-- 1.3.6.1.4.1.47477.10.21.5.3.10
		link5_R2AlarmPower OBJECT-TYPE
			SYNTAX DisplayString
			MAX-ACCESS read-write
			STATUS current
			DESCRIPTION
				"get or set the power alarm threshold of R2 in link5."
			::= { link5OBP 10 }


--  1.3.6.1.4.1.47477.10.21.5.3.29
		-- 1.3.6.1.4.1.47477.10.21.5.3.29
		link5_R3AlarmPower OBJECT-TYPE
			SYNTAX DisplayString
			MAX-ACCESS read-write
			STATUS current
			DESCRIPTION
				"get or set the power alarm threshold of R3 in link5."
			::= { link5OBP 29 }

		
--  1.3.6.1.4.1.47477.10.21.5.3.30
		-- 1.3.6.1.4.1.47477.10.21.5.3.30
		link5_R4AlarmPower OBJECT-TYPE
			SYNTAX DisplayString
			MAX-ACCESS read-write
			STATUS current
			DESCRIPTION
				"get or set the power alarm threshold of R4 in link5."
			::= { link5OBP 30 }

-- OBP4
--  1.3.6.1.4.1.47477.10.21.5.3.37
		-- 1.3.6.1.4.1.47477.10.21.5.3.37
		link5_1R1Power OBJECT-TYPE
			SYNTAX DisplayString
			MAX-ACCESS read-only
			STATUS current
			DESCRIPTION
				"get the power of 1R1 in link5."
			::= { link5OBP 37 }
			
--  1.3.6.1.4.1.47477.10.21.5.3.38
		-- 1.3.6.1.4.1.47477.10.21.5.3.38
		link5_1R2Power OBJECT-TYPE
			SYNTAX DisplayString
			MAX-ACCESS read-only
			STATUS current
			DESCRIPTION
				"get the power of 1R2 in link5."
			::= { link5OBP 38 }

--  1.3.6.1.4.1.47477.10.21.5.3.39
		-- 1.3.6.1.4.1.47477.10.21.5.3.39
		link5_1R3Power OBJECT-TYPE
			SYNTAX DisplayString
			MAX-ACCESS read-only
			STATUS current
			DESCRIPTION
				"get the power of 1R3 in link5."
			::= { link5OBP 39 }
			
--  1.3.6.1.4.1.47477.10.21.5.3.40
		-- 1.3.6.1.4.1.47477.10.21.5.3.40
		link5_1R4Power OBJECT-TYPE
			SYNTAX DisplayString
			MAX-ACCESS read-only
			STATUS current
			DESCRIPTION
				"get the power of 1R4 in link5."
			::= { link5OBP 40 }

--  1.3.6.1.4.1.47477.10.21.5.3.41
		-- 1.3.6.1.4.1.47477.10.21.5.3.41
		link5_2R1Power OBJECT-TYPE
			SYNTAX DisplayString
			MAX-ACCESS read-only
			STATUS current
			DESCRIPTION
				"get the power of 2R1 in link5."
			::= { link5OBP 41 }
			
--  1.3.6.1.4.1.47477.10.21.5.3.42
		-- 1.3.6.1.4.1.47477.10.21.5.3.42
		link5_2R2Power OBJECT-TYPE
			SYNTAX DisplayString
			MAX-ACCESS read-only
			STATUS current
			DESCRIPTION
				"get the power of 2R2 in link5."
			::= { link5OBP 42 }

--  1.3.6.1.4.1.47477.10.21.5.3.41
		-- 1.3.6.1.4.1.47477.10.21.5.3.43
		link5_2R3Power OBJECT-TYPE
			SYNTAX DisplayString
			MAX-ACCESS read-only
			STATUS current
			DESCRIPTION
				"get the power of 2R3 in link5."
			::= { link5OBP 43 }
			
--  1.3.6.1.4.1.47477.10.21.5.3.42
		-- 1.3.6.1.4.1.47477.10.21.5.3.44
		link5_2R4Power OBJECT-TYPE
			SYNTAX DisplayString
			MAX-ACCESS read-only
			STATUS current
			DESCRIPTION
				"get the power of 2R4 in link5."
			::= { link5OBP 44 }
			
--  1.3.6.1.4.1.47477.10.21.5.3.49
		-- 1.3.6.1.4.1.47477.10.21.5.3.49
		link5_1R1Wave OBJECT-TYPE
			SYNTAX INTEGER
				{
				w850nm(0),
				na(2)
				}
			MAX-ACCESS read-only
			STATUS current
			DESCRIPTION
				"get the wave length of 1R1 in link5."
			::= { link5OBP 49 }
		
--  1.3.6.1.4.1.47477.10.21.5.3.60
		-- 1.3.6.1.4.1.47477.10.21.5.3.60
		link5_1R2Wave OBJECT-TYPE
			SYNTAX INTEGER
				{
				w850nm(0),
				na(2)
				}
			MAX-ACCESS read-only
			STATUS current
			DESCRIPTION
				"get the wave length of 1R2 in link5."
			::= { link5OBP 60 }

--  1.3.6.1.4.1.47477.10.21.5.3.61
		-- 1.3.6.1.4.1.47477.10.21.5.3.61
		link5_1R3Wave OBJECT-TYPE
			SYNTAX INTEGER
				{
				w850nm(0),
				na(2)
				}
			MAX-ACCESS read-only
			STATUS current
			DESCRIPTION
				"get the wave length of 1R3 in link5."
			::= { link5OBP 61 }

		
--  1.3.6.1.4.1.47477.10.21.5.3.62
		-- 1.3.6.1.4.1.47477.10.21.5.3.62
		link5_1R4Wave OBJECT-TYPE
			SYNTAX INTEGER
				{
				w850nm(0),
				na(2)
				}
			MAX-ACCESS read-only
			STATUS current
			DESCRIPTION
				"get the wave length of 1R4 in link5."
			::= { link5OBP 62 }
	
--  1.3.6.1.4.1.47477.10.21.5.3.63
		-- 1.3.6.1.4.1.47477.10.21.5.3.63
		link5_2R1Wave OBJECT-TYPE
			SYNTAX INTEGER
				{
				w850nm(0),
				na(2)
				}
			MAX-ACCESS read-only
			STATUS current
			DESCRIPTION
				"get the wave length of 2R1 in link5."
			::= { link5OBP 63 }

		
--  1.3.6.1.4.1.47477.10.21.5.3.64
		-- 1.3.6.1.4.1.47477.10.21.5.3.64
		link5_2R2Wave OBJECT-TYPE
			SYNTAX INTEGER
				{
				w850nm(0),
				na(2)
				}
			MAX-ACCESS read-only
			STATUS current
			DESCRIPTION
				"get the wave length of 2R2 in link5."
			::= { link5OBP 64 }	
	
--  1.3.6.1.4.1.47477.10.21.5.3.65
		-- 1.3.6.1.4.1.47477.10.21.5.3.65
		link5_2R3Wave OBJECT-TYPE
			SYNTAX INTEGER
				{
				w850nm(0),
				na(2)
				}
			MAX-ACCESS read-only
			STATUS current
			DESCRIPTION
				"get the wave length of 2R3 in link5."
			::= { link5OBP 65 }

		
--  1.3.6.1.4.1.47477.10.21.5.3.66
		-- 1.3.6.1.4.1.47477.10.21.5.3.66
		link5_2R4Wave OBJECT-TYPE
			SYNTAX INTEGER
				{
				w850nm(0),
				na(2)
				}
			MAX-ACCESS read-only
			STATUS current
			DESCRIPTION
				"get the wave length of 2R4 in link5."
			::= { link5OBP 66 }	
			
--  1.3.6.1.4.1.47477.10.21.5.3.31
		-- 1.3.6.1.4.1.47477.10.21.5.3.31
		link5_1R1AlarmPower OBJECT-TYPE
			SYNTAX DisplayString
			MAX-ACCESS read-write
			STATUS current
			DESCRIPTION
				"get or set the power alarm threshold of 1R1 in link5."
			::= { link5OBP 31 }
			
--  1.3.6.1.4.1.47477.10.21.5.3.32
		-- 1.3.6.1.4.1.47477.10.21.5.3.32
		link5_1R2AlarmPower OBJECT-TYPE
			SYNTAX DisplayString
			MAX-ACCESS read-write
			STATUS current
			DESCRIPTION
				"get or set the power alarm threshold of 1R2 in link5."
			::= { link5OBP 32 }

--  1.3.6.1.4.1.47477.10.21.5.3.33
		-- 1.3.6.1.4.1.47477.10.21.5.3.33
		link5_1R3AlarmPower OBJECT-TYPE
			SYNTAX DisplayString
			MAX-ACCESS read-write
			STATUS current
			DESCRIPTION
				"get or set the power alarm threshold of 1R3 in link5."
			::= { link5OBP 33 }
			
--  1.3.6.1.4.1.47477.10.21.5.3.34
		-- 1.3.6.1.4.1.47477.10.21.5.3.34
		link5_1R4AlarmPower OBJECT-TYPE
			SYNTAX DisplayString
			MAX-ACCESS read-write
			STATUS current
			DESCRIPTION
				"get or set the power alarm threshold of 1R4 in link5."
			::= { link5OBP 34 }

--  1.3.6.1.4.1.47477.10.21.5.3.45
		-- 1.3.6.1.4.1.47477.10.21.5.3.45
		link5_2R1AlarmPower OBJECT-TYPE
			SYNTAX DisplayString
			MAX-ACCESS read-write
			STATUS current
			DESCRIPTION
				"get or set the power alarm threshold of 2R1 in link5."
			::= { link5OBP 45 }
			
--  1.3.6.1.4.1.47477.10.21.5.3.46
		-- 1.3.6.1.4.1.47477.10.21.5.3.46
		link5_2R2AlarmPower OBJECT-TYPE
			SYNTAX DisplayString
			MAX-ACCESS read-write
			STATUS current
			DESCRIPTION
				"get or set the power alarm threshold of 2R2 in link5."
			::= { link5OBP 46 }

--  1.3.6.1.4.1.47477.10.21.5.3.47
		-- 1.3.6.1.4.1.47477.10.21.5.3.47
		link5_2R3AlarmPower OBJECT-TYPE
			SYNTAX DisplayString
			MAX-ACCESS read-write
			STATUS current
			DESCRIPTION
				"get or set the power alarm threshold of 2R3 in link5."
			::= { link5OBP 47 }
			
--  1.3.6.1.4.1.47477.10.21.5.3.48
		-- 1.3.6.1.4.1.47477.10.21.5.3.48
		link5_2R4AlarmPower OBJECT-TYPE
			SYNTAX DisplayString
			MAX-ACCESS read-write
			STATUS current
			DESCRIPTION
				"get or set the power alarm threshold of 2R4 in link5."
			::= { link5OBP 48 }
			
--  1.3.6.1.4.1.47477.10.21.5.3.11
		-- 1.3.6.1.4.1.47477.10.21.5.3.11
		link5_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link5OBP 11 }
			
--  1.3.6.1.4.1.47477.10.21.5.3.67
		-- 1.3.6.1.4.1.47477.10.21.5.3.67
		link5_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link5OBP 67 }
			
--  1.3.6.1.4.1.47477.10.21.5.3.68
		-- 1.3.6.1.4.1.47477.10.21.5.3.68
		link5_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link5OBP 68 }
			
--  1.3.6.1.4.1.47477.10.21.5.3.12
		-- 1.3.6.1.4.1.47477.10.21.5.3.12
		link5_ReturnDelay OBJECT-TYPE
			--SYNTAX Integer32
			SYNTAX Integer32
			MAX-ACCESS read-write
			STATUS current
			DESCRIPTION
				"get or set how long link5 takes to return to automatic mode."
			::= { link5OBP 12 }
			
--  1.3.6.1.4.1.47477.10.21.5.3.13
		-- 1.3.6.1.4.1.47477.10.21.5.3.13
		link5_BackMode OBJECT-TYPE
			SYNTAX INTEGER
				{
				autoNoBack(0),
				autoBack(1)
				}
			MAX-ACCESS read-write
			STATUS current
			DESCRIPTION
				"get or set the back mode of link5."
			::= { link5OBP 13 }

		
--  1.3.6.1.4.1.47477.10.21.5.3.14
		-- 1.3.6.1.4.1.47477.10.21.5.3.14
		link5_BackDelay OBJECT-TYPE
			SYNTAX Integer32
			MAX-ACCESS read-write
			STATUS current
			DESCRIPTION
				"get or set the back delay."
			::= { link5OBP 14 }

--  1.3.6.1.4.1.47477.10.21.5.3.15
		-- 1.3.6.1.4.1.47477.10.21.5.3.15
		link5_ActiveHeartSwitch OBJECT-TYPE
			SYNTAX INTEGER
				{
				off(0),
				on(1)
				}
			MAX-ACCESS read-write
			STATUS current
			DESCRIPTION
				"get or set the switch status of active heartbeat."
			::= { link5OBP 15 }

		
--  1.3.6.1.4.1.47477.10.21.5.3.16
		-- 1.3.6.1.4.1.47477.10.21.5.3.16
		link5_ActiveSendInterval OBJECT-TYPE
			SYNTAX Integer32
			MAX-ACCESS read-write
			STATUS current
			DESCRIPTION
				"get or set the send interval of active heartbeat."
			::= { link5OBP 16 }		

--  1.3.6.1.4.1.47477.10.21.5.3.17
		-- 1.3.6.1.4.1.47477.10.21.5.3.17
		link5_ActiveTimeOut OBJECT-TYPE
			SYNTAX Integer32
			MAX-ACCESS read-write
			STATUS current
			DESCRIPTION
				"get or set how long the active heartbeat send timeout."
			::= { link5OBP 17 }

--  1.3.6.1.4.1.47477.10.21.5.3.18
		-- 1.3.6.1.4.1.47477.10.21.5.3.18
		link5_ActiveLossBypass OBJECT-TYPE
			SYNTAX Integer32
			MAX-ACCESS read-write
			STATUS current
			DESCRIPTION
				"get or set the bypass for active heartbeat packet loss."
			::= { link5OBP 18 }

--  1.3.6.1.4.1.47477.10.21.5.3.19
		-- 1.3.6.1.4.1.47477.10.21.5.3.19
		link5_PingIpAddress OBJECT-TYPE
			SYNTAX IpAddress
			MAX-ACCESS read-write
			STATUS current
			DESCRIPTION
				"get or set the ping ip address of link5."
			::= { link5OBP 19 }

--  1.3.6.1.4.1.47477.10.21.5.3.20
		-- 1.3.6.1.4.1.47477.10.21.5.3.20
		link5_PassiveHeartSwitch OBJECT-TYPE
			SYNTAX INTEGER
				{
				off(0),
				on(1)
				}
			MAX-ACCESS read-write
			STATUS current
			DESCRIPTION
				"get or set the switch status of passive heartbeat."
			::= { link5OBP 20 }
	

--  1.3.6.1.4.1.47477.10.21.5.3.21
		-- 1.3.6.1.4.1.47477.10.21.5.3.21
		link5_PassiveTimeOut OBJECT-TYPE
			SYNTAX Integer32
			MAX-ACCESS read-write
			STATUS current
			DESCRIPTION
				"get or set how long the passive heartbeat send timeout."
			::= { link5OBP 21 }

--  1.3.6.1.4.1.47477.10.21.5.3.22
		-- 1.3.6.1.4.1.47477.10.21.5.3.22
		link5_PassiveLossBypass OBJECT-TYPE
			SYNTAX Integer32
			MAX-ACCESS read-write
			STATUS current
			DESCRIPTION
				"get or set the bypass for passive heartbeat packet loss."
			::= { link5OBP 22 }

--  1.3.6.1.4.1.47477.10.21.5.3.23
		-- 1.3.6.1.4.1.47477.10.21.5.3.23
		link5_SwitchProtect OBJECT-TYPE
			SYNTAX INTEGER
				{
				off(0),
				on(1)
				}
			MAX-ACCESS read-write
			STATUS current
			DESCRIPTION
				"get or set the switch protection status of link5."
			::= { link5OBP 23 }
			
--  1.3.6.1.4.1.47477.10.21.5.3.24
		-- 1.3.6.1.4.1.47477.10.21.5.3.24
		link5_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link5OBP 24 }		

--  1.3.6.1.4.1.47477.10.21.5.3.25
		-- 1.3.6.1.4.1.47477.10.21.5.3.25
		link5_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link5OBP 25 }	

--  1.3.6.1.4.1.47477.10.21.5.3.26
		-- 1.3.6.1.4.1.47477.10.21.5.3.26
		link5_PowerAlarmStatus OBJECT-TYPE
			SYNTAX INTEGER
				{
				off(0),
				alarm(1),
				normal(2),
				na(3)
				}
			MAX-ACCESS read-only
			STATUS current
			DESCRIPTION
				"get whether a power alarm is generated."
			::= { link5OBP 26 }	


-- 1.3.6.1.4.1.47477.10.21.5.3.50.1
	link5_WorkModeChange 	OBJECT-TYPE    
    SYNTAX INTEGER	{
				manualMode(0),
				autoMode(1)
		}
	MAX-ACCESS read-only
	STATUS current
    DESCRIPTION
        "The Link mode Changed."
    ::= {link5OBPTrap 1}

-- 1.3.6.1.4.1.47477.10.21.5.3.50.2
	link5_StateChange 	OBJECT-TYPE    
    SYNTAX INTEGER	{
				bypass(0),
				primary(1)
		}
	MAX-ACCESS read-only
	STATUS current
    DESCRIPTION
        "The Link State(Channel) Changed."
    ::= {link5OBPTrap 2}

-- 1.3.6.1.4.1.47477.10.21.5.3.50.3
	link5_R1WaveSet 	OBJECT-TYPE    
    SYNTAX INTEGER	{
				w1310nm(0),
				w1550nm(1)
		}
	MAX-ACCESS read-only
	STATUS current
    DESCRIPTION
        "Set The link5 R1 Wave."
    ::= {link5OBPTrap 3}

-- 1.3.6.1.4.1.47477.10.21.5.3.50.4
	link5_R2WaveSet 	OBJECT-TYPE    
    SYNTAX INTEGER	{
				w1310nm(0),
				w1550nm(1)
		}
	MAX-ACCESS read-only
	STATUS current
    DESCRIPTION
        "Set The link5 R2 Wave."
    ::= {link5OBPTrap 4}			

-- 1.3.6.1.4.1.47477.10.21.5.3.50.5
	link5_R3WaveSet 	OBJECT-TYPE    
    SYNTAX INTEGER	{
				w1310nm(0),
				w1550nm(1)
		}
	MAX-ACCESS read-only
	STATUS current
    DESCRIPTION
        "Set The link5 R3 Wave."
    ::= {link5OBPTrap 5}

-- 1.3.6.1.4.1.47477.10.21.5.3.50.6
	link5_R4WaveSet 	OBJECT-TYPE    
    SYNTAX INTEGER	{
				w1310nm(0),
				w1550nm(1)
		}
	MAX-ACCESS read-only
	STATUS current
    DESCRIPTION
        "Set The link5 R4 Wave."
    ::= {link5OBPTrap 6}	
	
-- 1.3.6.1.4.1.47477.10.21.5.3.50.7
	link5_R1AlarmSet 	OBJECT-TYPE    
    SYNTAX DisplayString
	MAX-ACCESS read-only
	STATUS current
    DESCRIPTION
        "Set The link5 R1 Alarm Threshold."
    ::= {link5OBPTrap 7}

-- 1.3.6.1.4.1.47477.10.21.5.3.50.8
	link5_R2AlarmSet 	OBJECT-TYPE    
    SYNTAX DisplayString
	MAX-ACCESS read-only
	STATUS current
    DESCRIPTION
        "Set The link5 R2 Alarm Threshold."
    ::= {link5OBPTrap 8}
	
-- 1.3.6.1.4.1.47477.10.21.5.3.50.9
	link5_R3AlarmSet 	OBJECT-TYPE    
    SYNTAX DisplayString
	MAX-ACCESS read-only
	STATUS current
    DESCRIPTION
        "Set The link5 R3 Alarm Threshold."
    ::= {link5OBPTrap 9}

-- 1.3.6.1.4.1.47477.10.21.5.3.50.10
	link5_R4AlarmSet 	OBJECT-TYPE    
    SYNTAX DisplayString
	MAX-ACCESS read-only
	STATUS current
    DESCRIPTION
        "Set The link5 R4 Alarm Threshold."
    ::= {link5OBPTrap 10}	
	
	
-- 1.3.6.1.4.1.47477.10.21.5.3.50.11
	link5_1R1AlarmSet 	OBJECT-TYPE    
    SYNTAX DisplayString
	MAX-ACCESS read-only
	STATUS current
    DESCRIPTION
        "Set The link5 1R1 Alarm Threshold."
    ::= {link5OBPTrap 11}

-- 1.3.6.1.4.1.47477.10.21.5.3.50.12
	link5_2R1AlarmSet 	OBJECT-TYPE    
    SYNTAX DisplayString
	MAX-ACCESS read-only
	STATUS current
    DESCRIPTION
        "Set The link5 2R1 Alarm Threshold."
    ::= {link5OBPTrap 12}
	
-- 1.3.6.1.4.1.47477.10.21.5.3.50.13
	link5_1R2AlarmSet 	OBJECT-TYPE    
    SYNTAX DisplayString
	MAX-ACCESS read-only
	STATUS current
    DESCRIPTION
        "Set The link5 1R2 Alarm Threshold."
    ::= {link5OBPTrap 13}

-- 1.3.6.1.4.1.47477.10.21.5.3.50.14
	link5_2R2AlarmSet 	OBJECT-TYPE    
    SYNTAX DisplayString
	MAX-ACCESS read-only
	STATUS current
    DESCRIPTION
        "Set The link5 2R2 Alarm Threshold."
    ::= {link5OBPTrap 14}
	
-- 1.3.6.1.4.1.47477.10.21.5.3.50.15
	link5_1R3AlarmSet 	OBJECT-TYPE    
    SYNTAX DisplayString
	MAX-ACCESS read-only
	STATUS current
    DESCRIPTION
        "Set The link5 1R3 Alarm Threshold."
    ::= {link5OBPTrap 15}

-- 1.3.6.1.4.1.47477.10.21.5.3.50.16
	link5_2R3AlarmSet 	OBJECT-TYPE    
    SYNTAX DisplayString
	MAX-ACCESS read-only
	STATUS current
    DESCRIPTION
        "Set The link5 2R3 Alarm Threshold."
    ::= {link5OBPTrap 16}
	
-- 1.3.6.1.4.1.47477.10.21.5.3.50.17
	link5_1R4AlarmSet 	OBJECT-TYPE    
    SYNTAX DisplayString
	MAX-ACCESS read-only
	STATUS current
    DESCRIPTION
        "Set The link5 1R4 Alarm Threshold."
    ::= {link5OBPTrap 17}

-- 1.3.6.1.4.1.47477.10.21.5.3.50.18
	link5_2R4AlarmSet 	OBJECT-TYPE    
    SYNTAX DisplayString
	MAX-ACCESS read-only
	STATUS current
    DESCRIPTION
        "Set The link5 2R4 Alarm Threshold."
    ::= {link5OBPTrap 18}
	
-- 1.3.6.1.4.1.47477.10.21.5.3.50.19
	link5_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link5 PowerAlarmBypass2 Changed."
    ::= {link5OBPTrap 19}
	
-- 1.3.6.1.4.1.47477.10.21.5.3.50.20
	link5_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link5 PowerAlarmBypass4 Changed."
    ::= {link5OBPTrap 20}	
	
-- 1.3.6.1.4.1.47477.10.21.5.3.50.21
	link5_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link5 PowerAlarmBypass8 Changed."
    ::= {link5OBPTrap 21}
	
-- 1.3.6.1.4.1.47477.10.21.5.3.50.22
	link5_powerAlarmR1 	OBJECT-TYPE    
    SYNTAX DisplayString
	MAX-ACCESS read-only
	STATUS current
    DESCRIPTION
        "Set The link5 R1 Power Status Alarm."
    ::= {link5OBPTrap 22}
	
-- 1.3.6.1.4.1.47477.10.21.5.3.50.23
	link5_powerAlarmR2 	OBJECT-TYPE    
    SYNTAX DisplayString
	MAX-ACCESS read-only
	STATUS current
    DESCRIPTION
        "Set The link5 R2 Power Status Alarm."
    ::= {link5OBPTrap 23}
	
-- 1.3.6.1.4.1.47477.10.21.5.3.50.24
	link5_powerAlarmR3 	OBJECT-TYPE    
    SYNTAX DisplayString
	MAX-ACCESS read-only
	STATUS current
    DESCRIPTION
        "Set The link5 R3 Power Status Alarm."
    ::= {link5OBPTrap 24}
	
-- 1.3.6.1.4.1.47477.10.21.5.3.50.25
	link5_powerAlarmR4 	OBJECT-TYPE    
    SYNTAX DisplayString
	MAX-ACCESS read-only
	STATUS current
    DESCRIPTION
        "Set The link5 R4 Power Status Alarm."
    ::= {link5OBPTrap 25}
	
	
-- 1.3.6.1.4.1.47477.10.21.5.3.50.26
	link5_powerAlarm1R1 	OBJECT-TYPE    
    SYNTAX DisplayString
	MAX-ACCESS read-only
	STATUS current
    DESCRIPTION
        "Set The link5 1R1 Power Status Alarm."
    ::= {link5OBPTrap 26}
	
-- 1.3.6.1.4.1.47477.10.21.5.3.50.27
	link5_powerAlarm2R1 	OBJECT-TYPE    
    SYNTAX DisplayString
	MAX-ACCESS read-only
	STATUS current
    DESCRIPTION
        "Set The link5 2R1 Power Status Alarm."
    ::= {link5OBPTrap 27}
	
-- 1.3.6.1.4.1.47477.10.21.5.3.50.28
	link5_powerAlarm1R2 	OBJECT-TYPE    
    SYNTAX DisplayString
	MAX-ACCESS read-only
	STATUS current
    DESCRIPTION
        "Set The link5 1R2 Power Status Alarm."
    ::= {link5OBPTrap 28}
	
-- 1.3.6.1.4.1.47477.10.21.5.3.50.29
	link5_powerAlarm2R2 	OBJECT-TYPE    
    SYNTAX DisplayString
	MAX-ACCESS read-only
	STATUS current
    DESCRIPTION
        "Set The link5 2R2 Power Status Alarm."
    ::= {link5OBPTrap 29}
	
-- 1.3.6.1.4.1.47477.10.21.5.3.50.30
	link5_powerAlarm1R3 	OBJECT-TYPE    
    SYNTAX DisplayString
	MAX-ACCESS read-only
	STATUS current
    DESCRIPTION
        "Set The link5 1R3 Power Status Alarm."
    ::= {link5OBPTrap 30}
	
-- 1.3.6.1.4.1.47477.10.21.5.3.50.31
	link5_powerAlarm2R3 	OBJECT-TYPE    
    SYNTAX DisplayString
	MAX-ACCESS read-only
	STATUS current
    DESCRIPTION
        "Set The link5 2R1 Power Status Alarm."
    ::= {link5OBPTrap 31}
	
-- 1.3.6.1.4.1.47477.10.21.5.3.50.32
	link5_powerAlarm1R4 	OBJECT-TYPE    
    SYNTAX DisplayString
	MAX-ACCESS read-only
	STATUS current
    DESCRIPTION
        "Set The link5 1R4 Power Status Alarm."
    ::= {link5OBPTrap 32}
	
-- 1.3.6.1.4.1.47477.10.21.5.3.50.33
	link5_powerAlarm2R4 	OBJECT-TYPE    
    SYNTAX DisplayString
	MAX-ACCESS read-only
	STATUS current
    DESCRIPTION
        "Set The link5 2R4 Power Status Alarm."
    ::= {link5OBPTrap 33}
	
--  1.3.6.1.4.1.47477.10.21.6.3.1
		-- 1.3.6.1.4.1.47477.10.21.6.3.1
		link6_State OBJECT-TYPE
			SYNTAX INTEGER
				{
				off(0),
				on(1)
				}
			MAX-ACCESS read-only
			STATUS current
			DESCRIPTION
				"get the information about whether link6 is working."
			::= { link6OBP 1 }

		
--  1.3.6.1.4.1.47477.10.21.6.3.2
		-- 1.3.6.1.4.1.47477.10.21.6.3.2
		link6_DeviceType OBJECT-TYPE
			SYNTAX DisplayString
			MAX-ACCESS read-only
			STATUS current
			DESCRIPTION
				"get the type of card in link6."
			::= { link6OBP 2 }

			
--  1.3.6.1.4.1.47477.10.21.6.3.3
		-- 1.3.6.1.4.1.47477.10.21.6.3.3
		link6_WorkMode OBJECT-TYPE
			SYNTAX INTEGER
				{
				manualMode(0),
				autoMode(1)
				}
			MAX-ACCESS read-write
			STATUS current
			DESCRIPTION
				"get or set link6's work mode."
			::= { link6OBP 3 }

		
--  1.3.6.1.4.1.47477.10.21.6.3.4
		-- 1.3.6.1.4.1.47477.10.21.6.3.4
		link6_Channel OBJECT-TYPE
			SYNTAX INTEGER
				{
				bypass(0),
				primary(1)
				}
			MAX-ACCESS read-write
			STATUS current
			DESCRIPTION
				"get or set the channel in which link6 works."
			::= { link6OBP 4 }


--  1.3.6.1.4.1.47477.10.21.6.3.5
		-- 1.3.6.1.4.1.47477.10.21.6.3.5
		link6_R1Power OBJECT-TYPE
			SYNTAX DisplayString
			MAX-ACCESS read-only
			STATUS current
			DESCRIPTION
				"get the power of R1 in link6."
			::= { link6OBP 5 }

		
--  1.3.6.1.4.1.47477.10.21.6.3.6
		-- 1.3.6.1.4.1.47477.10.21.6.3.6
		link6_R2Power OBJECT-TYPE
			SYNTAX DisplayString
			MAX-ACCESS read-only
			STATUS current
			DESCRIPTION
				"get the power of R2 in link6."
			::= { link6OBP 6 }
			
--  1.3.6.1.4.1.47477.10.21.6.3.35
		-- 1.3.6.1.4.1.47477.10.21.6.3.35
		link6_R3Power OBJECT-TYPE
			SYNTAX DisplayString
			MAX-ACCESS read-only
			STATUS current
			DESCRIPTION
				"get the power of R3 in link6."
			::= { link6OBP 35 }
			
--  1.3.6.1.4.1.47477.10.21.6.3.36
		-- 1.3.6.1.4.1.47477.10.21.6.3.36
		link6_R4Power OBJECT-TYPE
			SYNTAX DisplayString
			MAX-ACCESS read-only
			STATUS current
			DESCRIPTION
				"get the power of R4 in link6."
			::= { link6OBP 36 }		
		
--  1.3.6.1.4.1.47477.10.21.6.3.7
		-- 1.3.6.1.4.1.47477.10.21.6.3.7
		link6_R1Wave OBJECT-TYPE
			SYNTAX INTEGER
				{
				w1310nm(0),
				w1550nm(1),
				na(2)
				}
			MAX-ACCESS read-write
			STATUS current
			DESCRIPTION
				"get or set the wave length of R1 in link6."
			::= { link6OBP 7 }

		
--  1.3.6.1.4.1.47477.10.21.6.3.8
		-- 1.3.6.1.4.1.47477.10.21.6.3.8
		link6_R2Wave OBJECT-TYPE
			SYNTAX INTEGER
				{
				w1310nm(0),
				w1550nm(1),
				na(2)
				}
			MAX-ACCESS read-write
			STATUS current
			DESCRIPTION
				"get or set the wave length of R2 in link6."
			::= { link6OBP 8 }


--  1.3.6.1.4.1.47477.10.21.6.3.27
		-- 1.3.6.1.4.1.47477.10.21.6.3.27
		link6_R3Wave OBJECT-TYPE
			SYNTAX INTEGER
				{
				w1310nm(0),
				w1550nm(1),
				na(2)
				}
			MAX-ACCESS read-write
			STATUS current
			DESCRIPTION
				"get or set the wave length of R3 in link6."
			::= { link6OBP 27 }

		
--  1.3.6.1.4.1.47477.10.21.6.3.28
		-- 1.3.6.1.4.1.47477.10.21.6.3.28
		link6_R4Wave OBJECT-TYPE
			SYNTAX INTEGER
				{
				w1310nm(0),
				w1550nm(1),
				na(2)
				}
			MAX-ACCESS read-write
			STATUS current
			DESCRIPTION
				"get or set the wave length of R4 in link6."
			::= { link6OBP 28 }
			
--  1.3.6.1.4.1.47477.10.21.6.3.9
		-- 1.3.6.1.4.1.47477.10.21.6.3.9
		link6_R1AlarmPower OBJECT-TYPE
			SYNTAX DisplayString
			MAX-ACCESS read-write
			STATUS current
			DESCRIPTION
				"get or set the power alarm threshold of R1 in link6."
			::= { link6OBP 9 }

		
--  1.3.6.1.4.1.47477.10.21.6.3.10
		-- 1.3.6.1.4.1.47477.10.21.6.3.10
		link6_R2AlarmPower OBJECT-TYPE
			SYNTAX DisplayString
			MAX-ACCESS read-write
			STATUS current
			DESCRIPTION
				"get or set the power alarm threshold of R2 in link6."
			::= { link6OBP 10 }


--  1.3.6.1.4.1.47477.10.21.6.3.29
		-- 1.3.6.1.4.1.47477.10.21.6.3.29
		link6_R3AlarmPower OBJECT-TYPE
			SYNTAX DisplayString
			MAX-ACCESS read-write
			STATUS current
			DESCRIPTION
				"get or set the power alarm threshold of R3 in link6."
			::= { link6OBP 29 }

		
--  1.3.6.1.4.1.47477.10.21.6.3.30
		-- 1.3.6.1.4.1.47477.10.21.6.3.30
		link6_R4AlarmPower OBJECT-TYPE
			SYNTAX DisplayString
			MAX-ACCESS read-write
			STATUS current
			DESCRIPTION
				"get or set the power alarm threshold of R4 in link6."
			::= { link6OBP 30 }

-- OBP4
--  1.3.6.1.4.1.47477.10.21.6.3.37
		-- 1.3.6.1.4.1.47477.10.21.6.3.37
		link6_1R1Power OBJECT-TYPE
			SYNTAX DisplayString
			MAX-ACCESS read-only
			STATUS current
			DESCRIPTION
				"get the power of 1R1 in link6."
			::= { link6OBP 37 }
			
--  1.3.6.1.4.1.47477.10.21.6.3.38
		-- 1.3.6.1.4.1.47477.10.21.6.3.38
		link6_1R2Power OBJECT-TYPE
			SYNTAX DisplayString
			MAX-ACCESS read-only
			STATUS current
			DESCRIPTION
				"get the power of 1R2 in link6."
			::= { link6OBP 38 }

--  1.3.6.1.4.1.47477.10.21.6.3.39
		-- 1.3.6.1.4.1.47477.10.21.6.3.39
		link6_1R3Power OBJECT-TYPE
			SYNTAX DisplayString
			MAX-ACCESS read-only
			STATUS current
			DESCRIPTION
				"get the power of 1R3 in link6."
			::= { link6OBP 39 }
			
--  1.3.6.1.4.1.47477.10.21.6.3.40
		-- 1.3.6.1.4.1.47477.10.21.6.3.40
		link6_1R4Power OBJECT-TYPE
			SYNTAX DisplayString
			MAX-ACCESS read-only
			STATUS current
			DESCRIPTION
				"get the power of 1R4 in link6."
			::= { link6OBP 40 }

--  1.3.6.1.4.1.47477.10.21.6.3.41
		-- 1.3.6.1.4.1.47477.10.21.6.3.41
		link6_2R1Power OBJECT-TYPE
			SYNTAX DisplayString
			MAX-ACCESS read-only
			STATUS current
			DESCRIPTION
				"get the power of 2R1 in link6."
			::= { link6OBP 41 }
			
--  1.3.6.1.4.1.47477.10.21.6.3.42
		-- 1.3.6.1.4.1.47477.10.21.6.3.42
		link6_2R2Power OBJECT-TYPE
			SYNTAX DisplayString
			MAX-ACCESS read-only
			STATUS current
			DESCRIPTION
				"get the power of 2R2 in link6."
			::= { link6OBP 42 }

--  1.3.6.1.4.1.47477.10.21.6.3.41
		-- 1.3.6.1.4.1.47477.10.21.6.3.43
		link6_2R3Power OBJECT-TYPE
			SYNTAX DisplayString
			MAX-ACCESS read-only
			STATUS current
			DESCRIPTION
				"get the power of 2R3 in link6."
			::= { link6OBP 43 }
			
--  1.3.6.1.4.1.47477.10.21.6.3.42
		-- 1.3.6.1.4.1.47477.10.21.6.3.44
		link6_2R4Power OBJECT-TYPE
			SYNTAX DisplayString
			MAX-ACCESS read-only
			STATUS current
			DESCRIPTION
				"get the power of 2R4 in link6."
			::= { link6OBP 44 }
			
--  1.3.6.1.4.1.47477.10.21.6.3.49
		-- 1.3.6.1.4.1.47477.10.21.6.3.49
		link6_1R1Wave OBJECT-TYPE
			SYNTAX INTEGER
				{
				w850nm(0),
				na(2)
				}
			MAX-ACCESS read-only
			STATUS current
			DESCRIPTION
				"get the wave length of 1R1 in link6."
			::= { link6OBP 49 }
		
--  1.3.6.1.4.1.47477.10.21.6.3.60
		-- 1.3.6.1.4.1.47477.10.21.6.3.60
		link6_1R2Wave OBJECT-TYPE
			SYNTAX INTEGER
				{
				w850nm(0),
				na(2)
				}
			MAX-ACCESS read-only
			STATUS current
			DESCRIPTION
				"get the wave length of 1R2 in link6."
			::= { link6OBP 60 }

--  1.3.6.1.4.1.47477.10.21.6.3.61
		-- 1.3.6.1.4.1.47477.10.21.6.3.61
		link6_1R3Wave OBJECT-TYPE
			SYNTAX INTEGER
				{
				w850nm(0),
				na(2)
				}
			MAX-ACCESS read-only
			STATUS current
			DESCRIPTION
				"get the wave length of 1R3 in link6."
			::= { link6OBP 61 }

		
--  1.3.6.1.4.1.47477.10.21.6.3.62
		-- 1.3.6.1.4.1.47477.10.21.6.3.62
		link6_1R4Wave OBJECT-TYPE
			SYNTAX INTEGER
				{
				w850nm(0),
				na(2)
				}
			MAX-ACCESS read-only
			STATUS current
			DESCRIPTION
				"get the wave length of 1R4 in link6."
			::= { link6OBP 62 }
	
--  1.3.6.1.4.1.47477.10.21.6.3.63
		-- 1.3.6.1.4.1.47477.10.21.6.3.63
		link6_2R1Wave OBJECT-TYPE
			SYNTAX INTEGER
				{
				w850nm(0),
				na(2)
				}
			MAX-ACCESS read-only
			STATUS current
			DESCRIPTION
				"get the wave length of 2R1 in link6."
			::= { link6OBP 63 }

		
--  1.3.6.1.4.1.47477.10.21.6.3.64
		-- 1.3.6.1.4.1.47477.10.21.6.3.64
		link6_2R2Wave OBJECT-TYPE
			SYNTAX INTEGER
				{
				w850nm(0),
				na(2)
				}
			MAX-ACCESS read-only
			STATUS current
			DESCRIPTION
				"get the wave length of 2R2 in link6."
			::= { link6OBP 64 }	
	
--  1.3.6.1.4.1.47477.10.21.6.3.65
		-- 1.3.6.1.4.1.47477.10.21.6.3.65
		link6_2R3Wave OBJECT-TYPE
			SYNTAX INTEGER
				{
				w850nm(0),
				na(2)
				}
			MAX-ACCESS read-only
			STATUS current
			DESCRIPTION
				"get the wave length of 2R3 in link6."
			::= { link6OBP 65 }

		
--  1.3.6.1.4.1.47477.10.21.6.3.66
		-- 1.3.6.1.4.1.47477.10.21.6.3.66
		link6_2R4Wave OBJECT-TYPE
			SYNTAX INTEGER
				{
				w850nm(0),
				na(2)
				}
			MAX-ACCESS read-only
			STATUS current
			DESCRIPTION
				"get the wave length of 2R4 in link6."
			::= { link6OBP 66 }	
			
--  1.3.6.1.4.1.47477.10.21.6.3.31
		-- 1.3.6.1.4.1.47477.10.21.6.3.31
		link6_1R1AlarmPower OBJECT-TYPE
			SYNTAX DisplayString
			MAX-ACCESS read-write
			STATUS current
			DESCRIPTION
				"get or set the power alarm threshold of 1R1 in link6."
			::= { link6OBP 31 }
			
--  1.3.6.1.4.1.47477.10.21.6.3.32
		-- 1.3.6.1.4.1.47477.10.21.6.3.32
		link6_1R2AlarmPower OBJECT-TYPE
			SYNTAX DisplayString
			MAX-ACCESS read-write
			STATUS current
			DESCRIPTION
				"get or set the power alarm threshold of 1R2 in link6."
			::= { link6OBP 32 }

--  1.3.6.1.4.1.47477.10.21.6.3.33
		-- 1.3.6.1.4.1.47477.10.21.6.3.33
		link6_1R3AlarmPower OBJECT-TYPE
			SYNTAX DisplayString
			MAX-ACCESS read-write
			STATUS current
			DESCRIPTION
				"get or set the power alarm threshold of 1R3 in link6."
			::= { link6OBP 33 }
			
--  1.3.6.1.4.1.47477.10.21.6.3.34
		-- 1.3.6.1.4.1.47477.10.21.6.3.34
		link6_1R4AlarmPower OBJECT-TYPE
			SYNTAX DisplayString
			MAX-ACCESS read-write
			STATUS current
			DESCRIPTION
				"get or set the power alarm threshold of 1R4 in link6."
			::= { link6OBP 34 }

--  1.3.6.1.4.1.47477.10.21.6.3.45
		-- 1.3.6.1.4.1.47477.10.21.6.3.45
		link6_2R1AlarmPower OBJECT-TYPE
			SYNTAX DisplayString
			MAX-ACCESS read-write
			STATUS current
			DESCRIPTION
				"get or set the power alarm threshold of 2R1 in link6."
			::= { link6OBP 45 }
			
--  1.3.6.1.4.1.47477.10.21.6.3.46
		-- 1.3.6.1.4.1.47477.10.21.6.3.46
		link6_2R2AlarmPower OBJECT-TYPE
			SYNTAX DisplayString
			MAX-ACCESS read-write
			STATUS current
			DESCRIPTION
				"get or set the power alarm threshold of 2R2 in link6."
			::= { link6OBP 46 }

--  1.3.6.1.4.1.47477.10.21.6.3.47
		-- 1.3.6.1.4.1.47477.10.21.6.3.47
		link6_2R3AlarmPower OBJECT-TYPE
			SYNTAX DisplayString
			MAX-ACCESS read-write
			STATUS current
			DESCRIPTION
				"get or set the power alarm threshold of 2R3 in link6."
			::= { link6OBP 47 }
			
--  1.3.6.1.4.1.47477.10.21.6.3.48
		-- 1.3.6.1.4.1.47477.10.21.6.3.48
		link6_2R4AlarmPower OBJECT-TYPE
			SYNTAX DisplayString
			MAX-ACCESS read-write
			STATUS current
			DESCRIPTION
				"get or set the power alarm threshold of 2R4 in link6."
			::= { link6OBP 48 }
			
--  1.3.6.1.4.1.47477.10.21.6.3.11
		-- 1.3.6.1.4.1.47477.10.21.6.3.11
		link6_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link6OBP 11 }
			
--  1.3.6.1.4.1.47477.10.21.6.3.67
		-- 1.3.6.1.4.1.47477.10.21.6.3.67
		link6_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link6OBP 67 }
			
--  1.3.6.1.4.1.47477.10.21.6.3.68
		-- 1.3.6.1.4.1.47477.10.21.6.3.68
		link6_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link6OBP 68 }
			
--  1.3.6.1.4.1.47477.10.21.6.3.12
		-- 1.3.6.1.4.1.47477.10.21.6.3.12
		link6_ReturnDelay OBJECT-TYPE
			--SYNTAX Integer32
			SYNTAX Integer32
			MAX-ACCESS read-write
			STATUS current
			DESCRIPTION
				"get or set how long link6 takes to return to automatic mode."
			::= { link6OBP 12 }
			
--  1.3.6.1.4.1.47477.10.21.6.3.13
		-- 1.3.6.1.4.1.47477.10.21.6.3.13
		link6_BackMode OBJECT-TYPE
			SYNTAX INTEGER
				{
				autoNoBack(0),
				autoBack(1)
				}
			MAX-ACCESS read-write
			STATUS current
			DESCRIPTION
				"get or set the back mode of link6."
			::= { link6OBP 13 }

		
--  1.3.6.1.4.1.47477.10.21.6.3.14
		-- 1.3.6.1.4.1.47477.10.21.6.3.14
		link6_BackDelay OBJECT-TYPE
			SYNTAX Integer32
			MAX-ACCESS read-write
			STATUS current
			DESCRIPTION
				"get or set the back delay."
			::= { link6OBP 14 }

--  1.3.6.1.4.1.47477.10.21.6.3.15
		-- 1.3.6.1.4.1.47477.10.21.6.3.15
		link6_ActiveHeartSwitch OBJECT-TYPE
			SYNTAX INTEGER
				{
				off(0),
				on(1)
				}
			MAX-ACCESS read-write
			STATUS current
			DESCRIPTION
				"get or set the switch status of active heartbeat."
			::= { link6OBP 15 }

		
--  1.3.6.1.4.1.47477.10.21.6.3.16
		-- 1.3.6.1.4.1.47477.10.21.6.3.16
		link6_ActiveSendInterval OBJECT-TYPE
			SYNTAX Integer32
			MAX-ACCESS read-write
			STATUS current
			DESCRIPTION
				"get or set the send interval of active heartbeat."
			::= { link6OBP 16 }		

--  1.3.6.1.4.1.47477.10.21.6.3.17
		-- 1.3.6.1.4.1.47477.10.21.6.3.17
		link6_ActiveTimeOut OBJECT-TYPE
			SYNTAX Integer32
			MAX-ACCESS read-write
			STATUS current
			DESCRIPTION
				"get or set how long the active heartbeat send timeout."
			::= { link6OBP 17 }

--  1.3.6.1.4.1.47477.10.21.6.3.18
		-- 1.3.6.1.4.1.47477.10.21.6.3.18
		link6_ActiveLossBypass OBJECT-TYPE
			SYNTAX Integer32
			MAX-ACCESS read-write
			STATUS current
			DESCRIPTION
				"get or set the bypass for active heartbeat packet loss."
			::= { link6OBP 18 }

--  1.3.6.1.4.1.47477.10.21.6.3.19
		-- 1.3.6.1.4.1.47477.10.21.6.3.19
		link6_PingIpAddress OBJECT-TYPE
			SYNTAX IpAddress
			MAX-ACCESS read-write
			STATUS current
			DESCRIPTION
				"get or set the ping ip address of link6."
			::= { link6OBP 19 }

--  1.3.6.1.4.1.47477.10.21.6.3.20
		-- 1.3.6.1.4.1.47477.10.21.6.3.20
		link6_PassiveHeartSwitch OBJECT-TYPE
			SYNTAX INTEGER
				{
				off(0),
				on(1)
				}
			MAX-ACCESS read-write
			STATUS current
			DESCRIPTION
				"get or set the switch status of passive heartbeat."
			::= { link6OBP 20 }
	

--  1.3.6.1.4.1.47477.10.21.6.3.21
		-- 1.3.6.1.4.1.47477.10.21.6.3.21
		link6_PassiveTimeOut OBJECT-TYPE
			SYNTAX Integer32
			MAX-ACCESS read-write
			STATUS current
			DESCRIPTION
				"get or set how long the passive heartbeat send timeout."
			::= { link6OBP 21 }

--  1.3.6.1.4.1.47477.10.21.6.3.22
		-- 1.3.6.1.4.1.47477.10.21.6.3.22
		link6_PassiveLossBypass OBJECT-TYPE
			SYNTAX Integer32
			MAX-ACCESS read-write
			STATUS current
			DESCRIPTION
				"get or set the bypass for passive heartbeat packet loss."
			::= { link6OBP 22 }

--  1.3.6.1.4.1.47477.10.21.6.3.23
		-- 1.3.6.1.4.1.47477.10.21.6.3.23
		link6_SwitchProtect OBJECT-TYPE
			SYNTAX INTEGER
				{
				off(0),
				on(1)
				}
			MAX-ACCESS read-write
			STATUS current
			DESCRIPTION
				"get or set the switch protection status of link6."
			::= { link6OBP 23 }
			
--  1.3.6.1.4.1.47477.10.21.6.3.24
		-- 1.3.6.1.4.1.47477.10.21.6.3.24
		link6_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link6OBP 24 }		

--  1.3.6.1.4.1.47477.10.21.6.3.25
		-- 1.3.6.1.4.1.47477.10.21.6.3.25
		link6_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link6OBP 25 }	

--  1.3.6.1.4.1.47477.10.21.6.3.26
		-- 1.3.6.1.4.1.47477.10.21.6.3.26
		link6_PowerAlarmStatus OBJECT-TYPE
			SYNTAX INTEGER
				{
				off(0),
				alarm(1),
				normal(2),
				na(3)
				}
			MAX-ACCESS read-only
			STATUS current
			DESCRIPTION
				"get whether a power alarm is generated."
			::= { link6OBP 26 }	


-- 1.3.6.1.4.1.47477.10.21.6.3.50.1
	link6_WorkModeChange 	OBJECT-TYPE    
    SYNTAX INTEGER	{
				manualMode(0),
				autoMode(1)
		}
	MAX-ACCESS read-only
	STATUS current
    DESCRIPTION
        "The Link mode Changed."
    ::= {link6OBPTrap 1}

-- 1.3.6.1.4.1.47477.10.21.6.3.50.2
	link6_StateChange 	OBJECT-TYPE    
    SYNTAX INTEGER	{
				bypass(0),
				primary(1)
		}
	MAX-ACCESS read-only
	STATUS current
    DESCRIPTION
        "The Link State(Channel) Changed."
    ::= {link6OBPTrap 2}

-- 1.3.6.1.4.1.47477.10.21.6.3.50.3
	link6_R1WaveSet 	OBJECT-TYPE    
    SYNTAX INTEGER	{
				w1310nm(0),
				w1550nm(1)
		}
	MAX-ACCESS read-only
	STATUS current
    DESCRIPTION
        "Set The link6 R1 Wave."
    ::= {link6OBPTrap 3}

-- 1.3.6.1.4.1.47477.10.21.6.3.50.4
	link6_R2WaveSet 	OBJECT-TYPE    
    SYNTAX INTEGER	{
				w1310nm(0),
				w1550nm(1)
		}
	MAX-ACCESS read-only
	STATUS current
    DESCRIPTION
        "Set The link6 R2 Wave."
    ::= {link6OBPTrap 4}			

-- 1.3.6.1.4.1.47477.10.21.6.3.50.5
	link6_R3WaveSet 	OBJECT-TYPE    
    SYNTAX INTEGER	{
				w1310nm(0),
				w1550nm(1)
		}
	MAX-ACCESS read-only
	STATUS current
    DESCRIPTION
        "Set The link6 R3 Wave."
    ::= {link6OBPTrap 5}

-- 1.3.6.1.4.1.47477.10.21.6.3.50.6
	link6_R4WaveSet 	OBJECT-TYPE    
    SYNTAX INTEGER	{
				w1310nm(0),
				w1550nm(1)
		}
	MAX-ACCESS read-only
	STATUS current
    DESCRIPTION
        "Set The link6 R4 Wave."
    ::= {link6OBPTrap 6}	
	
-- 1.3.6.1.4.1.47477.10.21.6.3.50.7
	link6_R1AlarmSet 	OBJECT-TYPE    
    SYNTAX DisplayString
	MAX-ACCESS read-only
	STATUS current
    DESCRIPTION
        "Set The link6 R1 Alarm Threshold."
    ::= {link6OBPTrap 7}

-- 1.3.6.1.4.1.47477.10.21.6.3.50.8
	link6_R2AlarmSet 	OBJECT-TYPE    
    SYNTAX DisplayString
	MAX-ACCESS read-only
	STATUS current
    DESCRIPTION
        "Set The link6 R2 Alarm Threshold."
    ::= {link6OBPTrap 8}
	
-- 1.3.6.1.4.1.47477.10.21.6.3.50.9
	link6_R3AlarmSet 	OBJECT-TYPE    
    SYNTAX DisplayString
	MAX-ACCESS read-only
	STATUS current
    DESCRIPTION
        "Set The link6 R3 Alarm Threshold."
    ::= {link6OBPTrap 9}

-- 1.3.6.1.4.1.47477.10.21.6.3.50.10
	link6_R4AlarmSet 	OBJECT-TYPE    
    SYNTAX DisplayString
	MAX-ACCESS read-only
	STATUS current
    DESCRIPTION
        "Set The link6 R4 Alarm Threshold."
    ::= {link6OBPTrap 10}	
	
	
-- 1.3.6.1.4.1.47477.10.21.6.3.50.11
	link6_1R1AlarmSet 	OBJECT-TYPE    
    SYNTAX DisplayString
	MAX-ACCESS read-only
	STATUS current
    DESCRIPTION
        "Set The link6 1R1 Alarm Threshold."
    ::= {link6OBPTrap 11}

-- 1.3.6.1.4.1.47477.10.21.6.3.50.12
	link6_2R1AlarmSet 	OBJECT-TYPE    
    SYNTAX DisplayString
	MAX-ACCESS read-only
	STATUS current
    DESCRIPTION
        "Set The link6 2R1 Alarm Threshold."
    ::= {link6OBPTrap 12}
	
-- 1.3.6.1.4.1.47477.10.21.6.3.50.13
	link6_1R2AlarmSet 	OBJECT-TYPE    
    SYNTAX DisplayString
	MAX-ACCESS read-only
	STATUS current
    DESCRIPTION
        "Set The link6 1R2 Alarm Threshold."
    ::= {link6OBPTrap 13}

-- 1.3.6.1.4.1.47477.10.21.6.3.50.14
	link6_2R2AlarmSet 	OBJECT-TYPE    
    SYNTAX DisplayString
	MAX-ACCESS read-only
	STATUS current
    DESCRIPTION
        "Set The link6 2R2 Alarm Threshold."
    ::= {link6OBPTrap 14}
	
-- 1.3.6.1.4.1.47477.10.21.6.3.50.15
	link6_1R3AlarmSet 	OBJECT-TYPE    
    SYNTAX DisplayString
	MAX-ACCESS read-only
	STATUS current
    DESCRIPTION
        "Set The link6 1R3 Alarm Threshold."
    ::= {link6OBPTrap 15}

-- 1.3.6.1.4.1.47477.10.21.6.3.50.16
	link6_2R3AlarmSet 	OBJECT-TYPE    
    SYNTAX DisplayString
	MAX-ACCESS read-only
	STATUS current
    DESCRIPTION
        "Set The link6 2R3 Alarm Threshold."
    ::= {link6OBPTrap 16}
	
-- 1.3.6.1.4.1.47477.10.21.6.3.50.17
	link6_1R4AlarmSet 	OBJECT-TYPE    
    SYNTAX DisplayString
	MAX-ACCESS read-only
	STATUS current
    DESCRIPTION
        "Set The link6 1R4 Alarm Threshold."
    ::= {link6OBPTrap 17}

-- 1.3.6.1.4.1.47477.10.21.6.3.50.18
	link6_2R4AlarmSet 	OBJECT-TYPE    
    SYNTAX DisplayString
	MAX-ACCESS read-only
	STATUS current
    DESCRIPTION
        "Set The link6 2R4 Alarm Threshold."
    ::= {link6OBPTrap 18}
	
-- 1.3.6.1.4.1.47477.10.21.6.3.50.19
	link6_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link6 PowerAlarmBypass2 Changed."
    ::= {link6OBPTrap 19}
	
-- 1.3.6.1.4.1.47477.10.21.6.3.50.20
	link6_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link6 PowerAlarmBypass4 Changed."
    ::= {link6OBPTrap 20}	
	
-- 1.3.6.1.4.1.47477.10.21.6.3.50.21
	link6_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link6 PowerAlarmBypass8 Changed."
    ::= {link6OBPTrap 21}
	
-- 1.3.6.1.4.1.47477.10.21.6.3.50.22
	link6_powerAlarmR1 	OBJECT-TYPE    
    SYNTAX DisplayString
	MAX-ACCESS read-only
	STATUS current
    DESCRIPTION
        "Set The link6 R1 Power Status Alarm."
    ::= {link6OBPTrap 22}
	
-- 1.3.6.1.4.1.47477.10.21.6.3.50.23
	link6_powerAlarmR2 	OBJECT-TYPE    
    SYNTAX DisplayString
	MAX-ACCESS read-only
	STATUS current
    DESCRIPTION
        "Set The link6 R2 Power Status Alarm."
    ::= {link6OBPTrap 23}
	
-- 1.3.6.1.4.1.47477.10.21.6.3.50.24
	link6_powerAlarmR3 	OBJECT-TYPE    
    SYNTAX DisplayString
	MAX-ACCESS read-only
	STATUS current
    DESCRIPTION
        "Set The link6 R3 Power Status Alarm."
    ::= {link6OBPTrap 24}
	
-- 1.3.6.1.4.1.47477.10.21.6.3.50.25
	link6_powerAlarmR4 	OBJECT-TYPE    
    SYNTAX DisplayString
	MAX-ACCESS read-only
	STATUS current
    DESCRIPTION
        "Set The link6 R4 Power Status Alarm."
    ::= {link6OBPTrap 25}
	
	
-- 1.3.6.1.4.1.47477.10.21.6.3.50.26
	link6_powerAlarm1R1 	OBJECT-TYPE    
    SYNTAX DisplayString
	MAX-ACCESS read-only
	STATUS current
    DESCRIPTION
        "Set The link6 1R1 Power Status Alarm."
    ::= {link6OBPTrap 26}
	
-- 1.3.6.1.4.1.47477.10.21.6.3.50.27
	link6_powerAlarm2R1 	OBJECT-TYPE    
    SYNTAX DisplayString
	MAX-ACCESS read-only
	STATUS current
    DESCRIPTION
        "Set The link6 2R1 Power Status Alarm."
    ::= {link6OBPTrap 27}
	
-- 1.3.6.1.4.1.47477.10.21.6.3.50.28
	link6_powerAlarm1R2 	OBJECT-TYPE    
    SYNTAX DisplayString
	MAX-ACCESS read-only
	STATUS current
    DESCRIPTION
        "Set The link6 1R2 Power Status Alarm."
    ::= {link6OBPTrap 28}
	
-- 1.3.6.1.4.1.47477.10.21.6.3.50.29
	link6_powerAlarm2R2 	OBJECT-TYPE    
    SYNTAX DisplayString
	MAX-ACCESS read-only
	STATUS current
    DESCRIPTION
        "Set The link6 2R2 Power Status Alarm."
    ::= {link6OBPTrap 29}
	
-- 1.3.6.1.4.1.47477.10.21.6.3.50.30
	link6_powerAlarm1R3 	OBJECT-TYPE    
    SYNTAX DisplayString
	MAX-ACCESS read-only
	STATUS current
    DESCRIPTION
        "Set The link6 1R3 Power Status Alarm."
    ::= {link6OBPTrap 30}
	
-- 1.3.6.1.4.1.47477.10.21.6.3.50.31
	link6_powerAlarm2R3 	OBJECT-TYPE    
    SYNTAX DisplayString
	MAX-ACCESS read-only
	STATUS current
    DESCRIPTION
        "Set The link6 2R1 Power Status Alarm."
    ::= {link6OBPTrap 31}
	
-- 1.3.6.1.4.1.47477.10.21.6.3.50.32
	link6_powerAlarm1R4 	OBJECT-TYPE    
    SYNTAX DisplayString
	MAX-ACCESS read-only
	STATUS current
    DESCRIPTION
        "Set The link6 1R4 Power Status Alarm."
    ::= {link6OBPTrap 32}
	
-- 1.3.6.1.4.1.47477.10.21.6.3.50.33
	link6_powerAlarm2R4 	OBJECT-TYPE    
    SYNTAX DisplayString
	MAX-ACCESS read-only
	STATUS current
    DESCRIPTION
        "Set The link6 2R4 Power Status Alarm."
    ::= {link6OBPTrap 33}
	
--  1.3.6.1.4.1.47477.10.21.7.3.1
		-- 1.3.6.1.4.1.47477.10.21.7.3.1
		link7_State OBJECT-TYPE
			SYNTAX INTEGER
				{
				off(0),
				on(1)
				}
			MAX-ACCESS read-only
			STATUS current
			DESCRIPTION
				"get the information about whether link7 is working."
			::= { link7OBP 1 }

		
--  1.3.6.1.4.1.47477.10.21.7.3.2
		-- 1.3.6.1.4.1.47477.10.21.7.3.2
		link7_DeviceType OBJECT-TYPE
			SYNTAX DisplayString
			MAX-ACCESS read-only
			STATUS current
			DESCRIPTION
				"get the type of card in link7."
			::= { link7OBP 2 }

			
--  1.3.6.1.4.1.47477.10.21.7.3.3
		-- 1.3.6.1.4.1.47477.10.21.7.3.3
		link7_WorkMode OBJECT-TYPE
			SYNTAX INTEGER
				{
				manualMode(0),
				autoMode(1)
				}
			MAX-ACCESS read-write
			STATUS current
			DESCRIPTION
				"get or set link7's work mode."
			::= { link7OBP 3 }

		
--  1.3.6.1.4.1.47477.10.21.7.3.4
		-- 1.3.6.1.4.1.47477.10.21.7.3.4
		link7_Channel OBJECT-TYPE
			SYNTAX INTEGER
				{
				bypass(0),
				primary(1)
				}
			MAX-ACCESS read-write
			STATUS current
			DESCRIPTION
				"get or set the channel in which link7 works."
			::= { link7OBP 4 }


--  1.3.6.1.4.1.47477.10.21.7.3.5
		-- 1.3.6.1.4.1.47477.10.21.7.3.5
		link7_R1Power OBJECT-TYPE
			SYNTAX DisplayString
			MAX-ACCESS read-only
			STATUS current
			DESCRIPTION
				"get the power of R1 in link7."
			::= { link7OBP 5 }

		
--  1.3.6.1.4.1.47477.10.21.7.3.6
		-- 1.3.6.1.4.1.47477.10.21.7.3.6
		link7_R2Power OBJECT-TYPE
			SYNTAX DisplayString
			MAX-ACCESS read-only
			STATUS current
			DESCRIPTION
				"get the power of R2 in link7."
			::= { link7OBP 6 }
			
--  1.3.6.1.4.1.47477.10.21.7.3.35
		-- 1.3.6.1.4.1.47477.10.21.7.3.35
		link7_R3Power OBJECT-TYPE
			SYNTAX DisplayString
			MAX-ACCESS read-only
			STATUS current
			DESCRIPTION
				"get the power of R3 in link7."
			::= { link7OBP 35 }
			
--  1.3.6.1.4.1.47477.10.21.7.3.36
		-- 1.3.6.1.4.1.47477.10.21.7.3.36
		link7_R4Power OBJECT-TYPE
			SYNTAX DisplayString
			MAX-ACCESS read-only
			STATUS current
			DESCRIPTION
				"get the power of R4 in link7."
			::= { link7OBP 36 }		
		
--  1.3.6.1.4.1.47477.10.21.7.3.7
		-- 1.3.6.1.4.1.47477.10.21.7.3.7
		link7_R1Wave OBJECT-TYPE
			SYNTAX INTEGER
				{
				w1310nm(0),
				w1550nm(1),
				na(2)
				}
			MAX-ACCESS read-write
			STATUS current
			DESCRIPTION
				"get or set the wave length of R1 in link7."
			::= { link7OBP 7 }

		
--  1.3.6.1.4.1.47477.10.21.7.3.8
		-- 1.3.6.1.4.1.47477.10.21.7.3.8
		link7_R2Wave OBJECT-TYPE
			SYNTAX INTEGER
				{
				w1310nm(0),
				w1550nm(1),
				na(2)
				}
			MAX-ACCESS read-write
			STATUS current
			DESCRIPTION
				"get or set the wave length of R2 in link7."
			::= { link7OBP 8 }


--  1.3.6.1.4.1.47477.10.21.7.3.27
		-- 1.3.6.1.4.1.47477.10.21.7.3.27
		link7_R3Wave OBJECT-TYPE
			SYNTAX INTEGER
				{
				w1310nm(0),
				w1550nm(1),
				na(2)
				}
			MAX-ACCESS read-write
			STATUS current
			DESCRIPTION
				"get or set the wave length of R3 in link7."
			::= { link7OBP 27 }

		
--  1.3.6.1.4.1.47477.10.21.7.3.28
		-- 1.3.6.1.4.1.47477.10.21.7.3.28
		link7_R4Wave OBJECT-TYPE
			SYNTAX INTEGER
				{
				w1310nm(0),
				w1550nm(1),
				na(2)
				}
			MAX-ACCESS read-write
			STATUS current
			DESCRIPTION
				"get or set the wave length of R4 in link7."
			::= { link7OBP 28 }
			
--  1.3.6.1.4.1.47477.10.21.7.3.9
		-- 1.3.6.1.4.1.47477.10.21.7.3.9
		link7_R1AlarmPower OBJECT-TYPE
			SYNTAX DisplayString
			MAX-ACCESS read-write
			STATUS current
			DESCRIPTION
				"get or set the power alarm threshold of R1 in link7."
			::= { link7OBP 9 }

		
--  1.3.6.1.4.1.47477.10.21.7.3.10
		-- 1.3.6.1.4.1.47477.10.21.7.3.10
		link7_R2AlarmPower OBJECT-TYPE
			SYNTAX DisplayString
			MAX-ACCESS read-write
			STATUS current
			DESCRIPTION
				"get or set the power alarm threshold of R2 in link7."
			::= { link7OBP 10 }


--  1.3.6.1.4.1.47477.10.21.7.3.29
		-- 1.3.6.1.4.1.47477.10.21.7.3.29
		link7_R3AlarmPower OBJECT-TYPE
			SYNTAX DisplayString
			MAX-ACCESS read-write
			STATUS current
			DESCRIPTION
				"get or set the power alarm threshold of R3 in link7."
			::= { link7OBP 29 }

		
--  1.3.6.1.4.1.47477.10.21.7.3.30
		-- 1.3.6.1.4.1.47477.10.21.7.3.30
		link7_R4AlarmPower OBJECT-TYPE
			SYNTAX DisplayString
			MAX-ACCESS read-write
			STATUS current
			DESCRIPTION
				"get or set the power alarm threshold of R4 in link7."
			::= { link7OBP 30 }

-- OBP4
--  1.3.6.1.4.1.47477.10.21.7.3.37
		-- 1.3.6.1.4.1.47477.10.21.7.3.37
		link7_1R1Power OBJECT-TYPE
			SYNTAX DisplayString
			MAX-ACCESS read-only
			STATUS current
			DESCRIPTION
				"get the power of 1R1 in link7."
			::= { link7OBP 37 }
			
--  1.3.6.1.4.1.47477.10.21.7.3.38
		-- 1.3.6.1.4.1.47477.10.21.7.3.38
		link7_1R2Power OBJECT-TYPE
			SYNTAX DisplayString
			MAX-ACCESS read-only
			STATUS current
			DESCRIPTION
				"get the power of 1R2 in link7."
			::= { link7OBP 38 }

--  1.3.6.1.4.1.47477.10.21.7.3.39
		-- 1.3.6.1.4.1.47477.10.21.7.3.39
		link7_1R3Power OBJECT-TYPE
			SYNTAX DisplayString
			MAX-ACCESS read-only
			STATUS current
			DESCRIPTION
				"get the power of 1R3 in link7."
			::= { link7OBP 39 }
			
--  1.3.6.1.4.1.47477.10.21.7.3.40
		-- 1.3.6.1.4.1.47477.10.21.7.3.40
		link7_1R4Power OBJECT-TYPE
			SYNTAX DisplayString
			MAX-ACCESS read-only
			STATUS current
			DESCRIPTION
				"get the power of 1R4 in link7."
			::= { link7OBP 40 }

--  1.3.6.1.4.1.47477.10.21.7.3.41
		-- 1.3.6.1.4.1.47477.10.21.7.3.41
		link7_2R1Power OBJECT-TYPE
			SYNTAX DisplayString
			MAX-ACCESS read-only
			STATUS current
			DESCRIPTION
				"get the power of 2R1 in link7."
			::= { link7OBP 41 }
			
--  1.3.6.1.4.1.47477.10.21.7.3.42
		-- 1.3.6.1.4.1.47477.10.21.7.3.42
		link7_2R2Power OBJECT-TYPE
			SYNTAX DisplayString
			MAX-ACCESS read-only
			STATUS current
			DESCRIPTION
				"get the power of 2R2 in link7."
			::= { link7OBP 42 }

--  1.3.6.1.4.1.47477.10.21.7.3.41
		-- 1.3.6.1.4.1.47477.10.21.7.3.43
		link7_2R3Power OBJECT-TYPE
			SYNTAX DisplayString
			MAX-ACCESS read-only
			STATUS current
			DESCRIPTION
				"get the power of 2R3 in link7."
			::= { link7OBP 43 }
			
--  1.3.6.1.4.1.47477.10.21.7.3.42
		-- 1.3.6.1.4.1.47477.10.21.7.3.44
		link7_2R4Power OBJECT-TYPE
			SYNTAX DisplayString
			MAX-ACCESS read-only
			STATUS current
			DESCRIPTION
				"get the power of 2R4 in link7."
			::= { link7OBP 44 }
			
--  1.3.6.1.4.1.47477.10.21.7.3.49
		-- 1.3.6.1.4.1.47477.10.21.7.3.49
		link7_1R1Wave OBJECT-TYPE
			SYNTAX INTEGER
				{
				w850nm(0),
				na(2)
				}
			MAX-ACCESS read-only
			STATUS current
			DESCRIPTION
				"get the wave length of 1R1 in link7."
			::= { link7OBP 49 }
		
--  1.3.6.1.4.1.47477.10.21.7.3.60
		-- 1.3.6.1.4.1.47477.10.21.7.3.60
		link7_1R2Wave OBJECT-TYPE
			SYNTAX INTEGER
				{
				w850nm(0),
				na(2)
				}
			MAX-ACCESS read-only
			STATUS current
			DESCRIPTION
				"get the wave length of 1R2 in link7."
			::= { link7OBP 60 }

--  1.3.6.1.4.1.47477.10.21.7.3.61
		-- 1.3.6.1.4.1.47477.10.21.7.3.61
		link7_1R3Wave OBJECT-TYPE
			SYNTAX INTEGER
				{
				w850nm(0),
				na(2)
				}
			MAX-ACCESS read-only
			STATUS current
			DESCRIPTION
				"get the wave length of 1R3 in link7."
			::= { link7OBP 61 }

		
--  1.3.6.1.4.1.47477.10.21.7.3.62
		-- 1.3.6.1.4.1.47477.10.21.7.3.62
		link7_1R4Wave OBJECT-TYPE
			SYNTAX INTEGER
				{
				w850nm(0),
				na(2)
				}
			MAX-ACCESS read-only
			STATUS current
			DESCRIPTION
				"get the wave length of 1R4 in link7."
			::= { link7OBP 62 }
	
--  1.3.6.1.4.1.47477.10.21.7.3.63
		-- 1.3.6.1.4.1.47477.10.21.7.3.63
		link7_2R1Wave OBJECT-TYPE
			SYNTAX INTEGER
				{
				w850nm(0),
				na(2)
				}
			MAX-ACCESS read-only
			STATUS current
			DESCRIPTION
				"get the wave length of 2R1 in link7."
			::= { link7OBP 63 }

		
--  1.3.6.1.4.1.47477.10.21.7.3.64
		-- 1.3.6.1.4.1.47477.10.21.7.3.64
		link7_2R2Wave OBJECT-TYPE
			SYNTAX INTEGER
				{
				w850nm(0),
				na(2)
				}
			MAX-ACCESS read-only
			STATUS current
			DESCRIPTION
				"get the wave length of 2R2 in link7."
			::= { link7OBP 64 }	
	
--  1.3.6.1.4.1.47477.10.21.7.3.65
		-- 1.3.6.1.4.1.47477.10.21.7.3.65
		link7_2R3Wave OBJECT-TYPE
			SYNTAX INTEGER
				{
				w850nm(0),
				na(2)
				}
			MAX-ACCESS read-only
			STATUS current
			DESCRIPTION
				"get the wave length of 2R3 in link7."
			::= { link7OBP 65 }

		
--  1.3.6.1.4.1.47477.10.21.7.3.66
		-- 1.3.6.1.4.1.47477.10.21.7.3.66
		link7_2R4Wave OBJECT-TYPE
			SYNTAX INTEGER
				{
				w850nm(0),
				na(2)
				}
			MAX-ACCESS read-only
			STATUS current
			DESCRIPTION
				"get the wave length of 2R4 in link7."
			::= { link7OBP 66 }	
			
--  1.3.6.1.4.1.47477.10.21.7.3.31
		-- 1.3.6.1.4.1.47477.10.21.7.3.31
		link7_1R1AlarmPower OBJECT-TYPE
			SYNTAX DisplayString
			MAX-ACCESS read-write
			STATUS current
			DESCRIPTION
				"get or set the power alarm threshold of 1R1 in link7."
			::= { link7OBP 31 }
			
--  1.3.6.1.4.1.47477.10.21.7.3.32
		-- 1.3.6.1.4.1.47477.10.21.7.3.32
		link7_1R2AlarmPower OBJECT-TYPE
			SYNTAX DisplayString
			MAX-ACCESS read-write
			STATUS current
			DESCRIPTION
				"get or set the power alarm threshold of 1R2 in link7."
			::= { link7OBP 32 }

--  1.3.6.1.4.1.47477.10.21.7.3.33
		-- 1.3.6.1.4.1.47477.10.21.7.3.33
		link7_1R3AlarmPower OBJECT-TYPE
			SYNTAX DisplayString
			MAX-ACCESS read-write
			STATUS current
			DESCRIPTION
				"get or set the power alarm threshold of 1R3 in link7."
			::= { link7OBP 33 }
			
--  1.3.6.1.4.1.47477.10.21.7.3.34
		-- 1.3.6.1.4.1.47477.10.21.7.3.34
		link7_1R4AlarmPower OBJECT-TYPE
			SYNTAX DisplayString
			MAX-ACCESS read-write
			STATUS current
			DESCRIPTION
				"get or set the power alarm threshold of 1R4 in link7."
			::= { link7OBP 34 }

--  1.3.6.1.4.1.47477.10.21.7.3.45
		-- 1.3.6.1.4.1.47477.10.21.7.3.45
		link7_2R1AlarmPower OBJECT-TYPE
			SYNTAX DisplayString
			MAX-ACCESS read-write
			STATUS current
			DESCRIPTION
				"get or set the power alarm threshold of 2R1 in link7."
			::= { link7OBP 45 }
			
--  1.3.6.1.4.1.47477.10.21.7.3.46
		-- 1.3.6.1.4.1.47477.10.21.7.3.46
		link7_2R2AlarmPower OBJECT-TYPE
			SYNTAX DisplayString
			MAX-ACCESS read-write
			STATUS current
			DESCRIPTION
				"get or set the power alarm threshold of 2R2 in link7."
			::= { link7OBP 46 }

--  1.3.6.1.4.1.47477.10.21.7.3.47
		-- 1.3.6.1.4.1.47477.10.21.7.3.47
		link7_2R3AlarmPower OBJECT-TYPE
			SYNTAX DisplayString
			MAX-ACCESS read-write
			STATUS current
			DESCRIPTION
				"get or set the power alarm threshold of 2R3 in link7."
			::= { link7OBP 47 }
			
--  1.3.6.1.4.1.47477.10.21.7.3.48
		-- 1.3.6.1.4.1.47477.10.21.7.3.48
		link7_2R4AlarmPower OBJECT-TYPE
			SYNTAX DisplayString
			MAX-ACCESS read-write
			STATUS current
			DESCRIPTION
				"get or set the power alarm threshold of 2R4 in link7."
			::= { link7OBP 48 }
			
--  1.3.6.1.4.1.47477.10.21.7.3.11
		-- 1.3.6.1.4.1.47477.10.21.7.3.11
		link7_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link7OBP 11 }
			
--  1.3.6.1.4.1.47477.10.21.7.3.67
		-- 1.3.6.1.4.1.47477.10.21.7.3.67
		link7_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link7OBP 67 }
			
--  1.3.6.1.4.1.47477.10.21.7.3.68
		-- 1.3.6.1.4.1.47477.10.21.7.3.68
		link7_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link7OBP 68 }
			
--  1.3.6.1.4.1.47477.10.21.7.3.12
		-- 1.3.6.1.4.1.47477.10.21.7.3.12
		link7_ReturnDelay OBJECT-TYPE
			--SYNTAX Integer32
			SYNTAX Integer32
			MAX-ACCESS read-write
			STATUS current
			DESCRIPTION
				"get or set how long link7 takes to return to automatic mode."
			::= { link7OBP 12 }
			
--  1.3.6.1.4.1.47477.10.21.7.3.13
		-- 1.3.6.1.4.1.47477.10.21.7.3.13
		link7_BackMode OBJECT-TYPE
			SYNTAX INTEGER
				{
				autoNoBack(0),
				autoBack(1)
				}
			MAX-ACCESS read-write
			STATUS current
			DESCRIPTION
				"get or set the back mode of link7."
			::= { link7OBP 13 }

		
--  1.3.6.1.4.1.47477.10.21.7.3.14
		-- 1.3.6.1.4.1.47477.10.21.7.3.14
		link7_BackDelay OBJECT-TYPE
			SYNTAX Integer32
			MAX-ACCESS read-write
			STATUS current
			DESCRIPTION
				"get or set the back delay."
			::= { link7OBP 14 }

--  1.3.6.1.4.1.47477.10.21.7.3.15
		-- 1.3.6.1.4.1.47477.10.21.7.3.15
		link7_ActiveHeartSwitch OBJECT-TYPE
			SYNTAX INTEGER
				{
				off(0),
				on(1)
				}
			MAX-ACCESS read-write
			STATUS current
			DESCRIPTION
				"get or set the switch status of active heartbeat."
			::= { link7OBP 15 }

		
--  1.3.6.1.4.1.47477.10.21.7.3.16
		-- 1.3.6.1.4.1.47477.10.21.7.3.16
		link7_ActiveSendInterval OBJECT-TYPE
			SYNTAX Integer32
			MAX-ACCESS read-write
			STATUS current
			DESCRIPTION
				"get or set the send interval of active heartbeat."
			::= { link7OBP 16 }		

--  1.3.6.1.4.1.47477.10.21.7.3.17
		-- 1.3.6.1.4.1.47477.10.21.7.3.17
		link7_ActiveTimeOut OBJECT-TYPE
			SYNTAX Integer32
			MAX-ACCESS read-write
			STATUS current
			DESCRIPTION
				"get or set how long the active heartbeat send timeout."
			::= { link7OBP 17 }

--  1.3.6.1.4.1.47477.10.21.7.3.18
		-- 1.3.6.1.4.1.47477.10.21.7.3.18
		link7_ActiveLossBypass OBJECT-TYPE
			SYNTAX Integer32
			MAX-ACCESS read-write
			STATUS current
			DESCRIPTION
				"get or set the bypass for active heartbeat packet loss."
			::= { link7OBP 18 }

--  1.3.6.1.4.1.47477.10.21.7.3.19
		-- 1.3.6.1.4.1.47477.10.21.7.3.19
		link7_PingIpAddress OBJECT-TYPE
			SYNTAX IpAddress
			MAX-ACCESS read-write
			STATUS current
			DESCRIPTION
				"get or set the ping ip address of link7."
			::= { link7OBP 19 }

--  1.3.6.1.4.1.47477.10.21.7.3.20
		-- 1.3.6.1.4.1.47477.10.21.7.3.20
		link7_PassiveHeartSwitch OBJECT-TYPE
			SYNTAX INTEGER
				{
				off(0),
				on(1)
				}
			MAX-ACCESS read-write
			STATUS current
			DESCRIPTION
				"get or set the switch status of passive heartbeat."
			::= { link7OBP 20 }
	

--  1.3.6.1.4.1.47477.10.21.7.3.21
		-- 1.3.6.1.4.1.47477.10.21.7.3.21
		link7_PassiveTimeOut OBJECT-TYPE
			SYNTAX Integer32
			MAX-ACCESS read-write
			STATUS current
			DESCRIPTION
				"get or set how long the passive heartbeat send timeout."
			::= { link7OBP 21 }

--  1.3.6.1.4.1.47477.10.21.7.3.22
		-- 1.3.6.1.4.1.47477.10.21.7.3.22
		link7_PassiveLossBypass OBJECT-TYPE
			SYNTAX Integer32
			MAX-ACCESS read-write
			STATUS current
			DESCRIPTION
				"get or set the bypass for passive heartbeat packet loss."
			::= { link7OBP 22 }

--  1.3.6.1.4.1.47477.10.21.7.3.23
		-- 1.3.6.1.4.1.47477.10.21.7.3.23
		link7_SwitchProtect OBJECT-TYPE
			SYNTAX INTEGER
				{
				off(0),
				on(1)
				}
			MAX-ACCESS read-write
			STATUS current
			DESCRIPTION
				"get or set the switch protection status of link7."
			::= { link7OBP 23 }
			
--  1.3.6.1.4.1.47477.10.21.7.3.24
		-- 1.3.6.1.4.1.47477.10.21.7.3.24
		link7_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link7OBP 24 }		

--  1.3.6.1.4.1.47477.10.21.7.3.25
		-- 1.3.6.1.4.1.47477.10.21.7.3.25
		link7_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link7OBP 25 }	

--  1.3.6.1.4.1.47477.10.21.7.3.26
		-- 1.3.6.1.4.1.47477.10.21.7.3.26
		link7_PowerAlarmStatus OBJECT-TYPE
			SYNTAX INTEGER
				{
				off(0),
				alarm(1),
				normal(2),
				na(3)
				}
			MAX-ACCESS read-only
			STATUS current
			DESCRIPTION
				"get whether a power alarm is generated."
			::= { link7OBP 26 }	


-- 1.3.6.1.4.1.47477.10.21.7.3.50.1
	link7_WorkModeChange 	OBJECT-TYPE    
    SYNTAX INTEGER	{
				manualMode(0),
				autoMode(1)
		}
	MAX-ACCESS read-only
	STATUS current
    DESCRIPTION
        "The Link mode Changed."
    ::= {link7OBPTrap 1}

-- 1.3.6.1.4.1.47477.10.21.7.3.50.2
	link7_StateChange 	OBJECT-TYPE    
    SYNTAX INTEGER	{
				bypass(0),
				primary(1)
		}
	MAX-ACCESS read-only
	STATUS current
    DESCRIPTION
        "The Link State(Channel) Changed."
    ::= {link7OBPTrap 2}

-- 1.3.6.1.4.1.47477.10.21.7.3.50.3
	link7_R1WaveSet 	OBJECT-TYPE    
    SYNTAX INTEGER	{
				w1310nm(0),
				w1550nm(1)
		}
	MAX-ACCESS read-only
	STATUS current
    DESCRIPTION
        "Set The link7 R1 Wave."
    ::= {link7OBPTrap 3}

-- 1.3.6.1.4.1.47477.10.21.7.3.50.4
	link7_R2WaveSet 	OBJECT-TYPE    
    SYNTAX INTEGER	{
				w1310nm(0),
				w1550nm(1)
		}
	MAX-ACCESS read-only
	STATUS current
    DESCRIPTION
        "Set The link7 R2 Wave."
    ::= {link7OBPTrap 4}			

-- 1.3.6.1.4.1.47477.10.21.7.3.50.5
	link7_R3WaveSet 	OBJECT-TYPE    
    SYNTAX INTEGER	{
				w1310nm(0),
				w1550nm(1)
		}
	MAX-ACCESS read-only
	STATUS current
    DESCRIPTION
        "Set The link7 R3 Wave."
    ::= {link7OBPTrap 5}

-- 1.3.6.1.4.1.47477.10.21.7.3.50.6
	link7_R4WaveSet 	OBJECT-TYPE    
    SYNTAX INTEGER	{
				w1310nm(0),
				w1550nm(1)
		}
	MAX-ACCESS read-only
	STATUS current
    DESCRIPTION
        "Set The link7 R4 Wave."
    ::= {link7OBPTrap 6}	
	
-- 1.3.6.1.4.1.47477.10.21.7.3.50.7
	link7_R1AlarmSet 	OBJECT-TYPE    
    SYNTAX DisplayString
	MAX-ACCESS read-only
	STATUS current
    DESCRIPTION
        "Set The link7 R1 Alarm Threshold."
    ::= {link7OBPTrap 7}

-- 1.3.6.1.4.1.47477.10.21.7.3.50.8
	link7_R2AlarmSet 	OBJECT-TYPE    
    SYNTAX DisplayString
	MAX-ACCESS read-only
	STATUS current
    DESCRIPTION
        "Set The link7 R2 Alarm Threshold."
    ::= {link7OBPTrap 8}
	
-- 1.3.6.1.4.1.47477.10.21.7.3.50.9
	link7_R3AlarmSet 	OBJECT-TYPE    
    SYNTAX DisplayString
	MAX-ACCESS read-only
	STATUS current
    DESCRIPTION
        "Set The link7 R3 Alarm Threshold."
    ::= {link7OBPTrap 9}

-- 1.3.6.1.4.1.47477.10.21.7.3.50.10
	link7_R4AlarmSet 	OBJECT-TYPE    
    SYNTAX DisplayString
	MAX-ACCESS read-only
	STATUS current
    DESCRIPTION
        "Set The link7 R4 Alarm Threshold."
    ::= {link7OBPTrap 10}	
	
	
-- 1.3.6.1.4.1.47477.10.21.7.3.50.11
	link7_1R1AlarmSet 	OBJECT-TYPE    
    SYNTAX DisplayString
	MAX-ACCESS read-only
	STATUS current
    DESCRIPTION
        "Set The link7 1R1 Alarm Threshold."
    ::= {link7OBPTrap 11}

-- 1.3.6.1.4.1.47477.10.21.7.3.50.12
	link7_2R1AlarmSet 	OBJECT-TYPE    
    SYNTAX DisplayString
	MAX-ACCESS read-only
	STATUS current
    DESCRIPTION
        "Set The link7 2R1 Alarm Threshold."
    ::= {link7OBPTrap 12}
	
-- 1.3.6.1.4.1.47477.10.21.7.3.50.13
	link7_1R2AlarmSet 	OBJECT-TYPE    
    SYNTAX DisplayString
	MAX-ACCESS read-only
	STATUS current
    DESCRIPTION
        "Set The link7 1R2 Alarm Threshold."
    ::= {link7OBPTrap 13}

-- 1.3.6.1.4.1.47477.10.21.7.3.50.14
	link7_2R2AlarmSet 	OBJECT-TYPE    
    SYNTAX DisplayString
	MAX-ACCESS read-only
	STATUS current
    DESCRIPTION
        "Set The link7 2R2 Alarm Threshold."
    ::= {link7OBPTrap 14}
	
-- 1.3.6.1.4.1.47477.10.21.7.3.50.15
	link7_1R3AlarmSet 	OBJECT-TYPE    
    SYNTAX DisplayString
	MAX-ACCESS read-only
	STATUS current
    DESCRIPTION
        "Set The link7 1R3 Alarm Threshold."
    ::= {link7OBPTrap 15}

-- 1.3.6.1.4.1.47477.10.21.7.3.50.16
	link7_2R3AlarmSet 	OBJECT-TYPE    
    SYNTAX DisplayString
	MAX-ACCESS read-only
	STATUS current
    DESCRIPTION
        "Set The link7 2R3 Alarm Threshold."
    ::= {link7OBPTrap 16}
	
-- 1.3.6.1.4.1.47477.10.21.7.3.50.17
	link7_1R4AlarmSet 	OBJECT-TYPE    
    SYNTAX DisplayString
	MAX-ACCESS read-only
	STATUS current
    DESCRIPTION
        "Set The link7 1R4 Alarm Threshold."
    ::= {link7OBPTrap 17}

-- 1.3.6.1.4.1.47477.10.21.7.3.50.18
	link7_2R4AlarmSet 	OBJECT-TYPE    
    SYNTAX DisplayString
	MAX-ACCESS read-only
	STATUS current
    DESCRIPTION
        "Set The link7 2R4 Alarm Threshold."
    ::= {link7OBPTrap 18}
	
-- 1.3.6.1.4.1.47477.10.21.7.3.50.19
	link7_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link7 PowerAlarmBypass2 Changed."
    ::= {link7OBPTrap 19}
	
-- 1.3.6.1.4.1.47477.10.21.7.3.50.20
	link7_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link7 PowerAlarmBypass4 Changed."
    ::= {link7OBPTrap 20}	
	
-- 1.3.6.1.4.1.47477.10.21.7.3.50.21
	link7_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link7 PowerAlarmBypass8 Changed."
    ::= {link7OBPTrap 21}
	
-- 1.3.6.1.4.1.47477.10.21.7.3.50.22
	link7_powerAlarmR1 	OBJECT-TYPE    
    SYNTAX DisplayString
	MAX-ACCESS read-only
	STATUS current
    DESCRIPTION
        "Set The link7 R1 Power Status Alarm."
    ::= {link7OBPTrap 22}
	
-- 1.3.6.1.4.1.47477.10.21.7.3.50.23
	link7_powerAlarmR2 	OBJECT-TYPE    
    SYNTAX DisplayString
	MAX-ACCESS read-only
	STATUS current
    DESCRIPTION
        "Set The link7 R2 Power Status Alarm."
    ::= {link7OBPTrap 23}
	
-- 1.3.6.1.4.1.47477.10.21.7.3.50.24
	link7_powerAlarmR3 	OBJECT-TYPE    
    SYNTAX DisplayString
	MAX-ACCESS read-only
	STATUS current
    DESCRIPTION
        "Set The link7 R3 Power Status Alarm."
    ::= {link7OBPTrap 24}
	
-- 1.3.6.1.4.1.47477.10.21.7.3.50.25
	link7_powerAlarmR4 	OBJECT-TYPE    
    SYNTAX DisplayString
	MAX-ACCESS read-only
	STATUS current
    DESCRIPTION
        "Set The link7 R4 Power Status Alarm."
    ::= {link7OBPTrap 25}
	
	
-- 1.3.6.1.4.1.47477.10.21.7.3.50.26
	link7_powerAlarm1R1 	OBJECT-TYPE    
    SYNTAX DisplayString
	MAX-ACCESS read-only
	STATUS current
    DESCRIPTION
        "Set The link7 1R1 Power Status Alarm."
    ::= {link7OBPTrap 26}
	
-- 1.3.6.1.4.1.47477.10.21.7.3.50.27
	link7_powerAlarm2R1 	OBJECT-TYPE    
    SYNTAX DisplayString
	MAX-ACCESS read-only
	STATUS current
    DESCRIPTION
        "Set The link7 2R1 Power Status Alarm."
    ::= {link7OBPTrap 27}
	
-- 1.3.6.1.4.1.47477.10.21.7.3.50.28
	link7_powerAlarm1R2 	OBJECT-TYPE    
    SYNTAX DisplayString
	MAX-ACCESS read-only
	STATUS current
    DESCRIPTION
        "Set The link7 1R2 Power Status Alarm."
    ::= {link7OBPTrap 28}
	
-- 1.3.6.1.4.1.47477.10.21.7.3.50.29
	link7_powerAlarm2R2 	OBJECT-TYPE    
    SYNTAX DisplayString
	MAX-ACCESS read-only
	STATUS current
    DESCRIPTION
        "Set The link7 2R2 Power Status Alarm."
    ::= {link7OBPTrap 29}
	
-- 1.3.6.1.4.1.47477.10.21.7.3.50.30
	link7_powerAlarm1R3 	OBJECT-TYPE    
    SYNTAX DisplayString
	MAX-ACCESS read-only
	STATUS current
    DESCRIPTION
        "Set The link7 1R3 Power Status Alarm."
    ::= {link7OBPTrap 30}
	
-- 1.3.6.1.4.1.47477.10.21.7.3.50.31
	link7_powerAlarm2R3 	OBJECT-TYPE    
    SYNTAX DisplayString
	MAX-ACCESS read-only
	STATUS current
    DESCRIPTION
        "Set The link7 2R1 Power Status Alarm."
    ::= {link7OBPTrap 31}
	
-- 1.3.6.1.4.1.47477.10.21.7.3.50.32
	link7_powerAlarm1R4 	OBJECT-TYPE    
    SYNTAX DisplayString
	MAX-ACCESS read-only
	STATUS current
    DESCRIPTION
        "Set The link7 1R4 Power Status Alarm."
    ::= {link7OBPTrap 32}
	
-- 1.3.6.1.4.1.47477.10.21.7.3.50.33
	link7_powerAlarm2R4 	OBJECT-TYPE    
    SYNTAX DisplayString
	MAX-ACCESS read-only
	STATUS current
    DESCRIPTION
        "Set The link7 2R4 Power Status Alarm."
    ::= {link7OBPTrap 33}
	
--  1.3.6.1.4.1.47477.10.21.8.3.1
		-- 1.3.6.1.4.1.47477.10.21.8.3.1
		link8_State OBJECT-TYPE
			SYNTAX INTEGER
				{
				off(0),
				on(1)
				}
			MAX-ACCESS read-only
			STATUS current
			DESCRIPTION
				"get the information about whether link8 is working."
			::= { link8OBP 1 }

		
--  1.3.6.1.4.1.47477.10.21.8.3.2
		-- 1.3.6.1.4.1.47477.10.21.8.3.2
		link8_DeviceType OBJECT-TYPE
			SYNTAX DisplayString
			MAX-ACCESS read-only
			STATUS current
			DESCRIPTION
				"get the type of card in link8."
			::= { link8OBP 2 }

			
--  1.3.6.1.4.1.47477.10.21.8.3.3
		-- 1.3.6.1.4.1.47477.10.21.8.3.3
		link8_WorkMode OBJECT-TYPE
			SYNTAX INTEGER
				{
				manualMode(0),
				autoMode(1)
				}
			MAX-ACCESS read-write
			STATUS current
			DESCRIPTION
				"get or set link8's work mode."
			::= { link8OBP 3 }

		
--  1.3.6.1.4.1.47477.10.21.8.3.4
		-- 1.3.6.1.4.1.47477.10.21.8.3.4
		link8_Channel OBJECT-TYPE
			SYNTAX INTEGER
				{
				bypass(0),
				primary(1)
				}
			MAX-ACCESS read-write
			STATUS current
			DESCRIPTION
				"get or set the channel in which link8 works."
			::= { link8OBP 4 }


--  1.3.6.1.4.1.47477.10.21.8.3.5
		-- 1.3.6.1.4.1.47477.10.21.8.3.5
		link8_R1Power OBJECT-TYPE
			SYNTAX DisplayString
			MAX-ACCESS read-only
			STATUS current
			DESCRIPTION
				"get the power of R1 in link8."
			::= { link8OBP 5 }

		
--  1.3.6.1.4.1.47477.10.21.8.3.6
		-- 1.3.6.1.4.1.47477.10.21.8.3.6
		link8_R2Power OBJECT-TYPE
			SYNTAX DisplayString
			MAX-ACCESS read-only
			STATUS current
			DESCRIPTION
				"get the power of R2 in link8."
			::= { link8OBP 6 }
			
--  1.3.6.1.4.1.47477.10.21.8.3.35
		-- 1.3.6.1.4.1.47477.10.21.8.3.35
		link8_R3Power OBJECT-TYPE
			SYNTAX DisplayString
			MAX-ACCESS read-only
			STATUS current
			DESCRIPTION
				"get the power of R3 in link8."
			::= { link8OBP 35 }
			
--  1.3.6.1.4.1.47477.10.21.8.3.36
		-- 1.3.6.1.4.1.47477.10.21.8.3.36
		link8_R4Power OBJECT-TYPE
			SYNTAX DisplayString
			MAX-ACCESS read-only
			STATUS current
			DESCRIPTION
				"get the power of R4 in link8."
			::= { link8OBP 36 }		
		
--  1.3.6.1.4.1.47477.10.21.8.3.7
		-- 1.3.6.1.4.1.47477.10.21.8.3.7
		link8_R1Wave OBJECT-TYPE
			SYNTAX INTEGER
				{
				w1310nm(0),
				w1550nm(1),
				na(2)
				}
			MAX-ACCESS read-write
			STATUS current
			DESCRIPTION
				"get or set the wave length of R1 in link8."
			::= { link8OBP 7 }

		
--  1.3.6.1.4.1.47477.10.21.8.3.8
		-- 1.3.6.1.4.1.47477.10.21.8.3.8
		link8_R2Wave OBJECT-TYPE
			SYNTAX INTEGER
				{
				w1310nm(0),
				w1550nm(1),
				na(2)
				}
			MAX-ACCESS read-write
			STATUS current
			DESCRIPTION
				"get or set the wave length of R2 in link8."
			::= { link8OBP 8 }


--  1.3.6.1.4.1.47477.10.21.8.3.27
		-- 1.3.6.1.4.1.47477.10.21.8.3.27
		link8_R3Wave OBJECT-TYPE
			SYNTAX INTEGER
				{
				w1310nm(0),
				w1550nm(1),
				na(2)
				}
			MAX-ACCESS read-write
			STATUS current
			DESCRIPTION
				"get or set the wave length of R3 in link8."
			::= { link8OBP 27 }

		
--  1.3.6.1.4.1.47477.10.21.8.3.28
		-- 1.3.6.1.4.1.47477.10.21.8.3.28
		link8_R4Wave OBJECT-TYPE
			SYNTAX INTEGER
				{
				w1310nm(0),
				w1550nm(1),
				na(2)
				}
			MAX-ACCESS read-write
			STATUS current
			DESCRIPTION
				"get or set the wave length of R4 in link8."
			::= { link8OBP 28 }
			
--  1.3.6.1.4.1.47477.10.21.8.3.9
		-- 1.3.6.1.4.1.47477.10.21.8.3.9
		link8_R1AlarmPower OBJECT-TYPE
			SYNTAX DisplayString
			MAX-ACCESS read-write
			STATUS current
			DESCRIPTION
				"get or set the power alarm threshold of R1 in link8."
			::= { link8OBP 9 }

		
--  1.3.6.1.4.1.47477.10.21.8.3.10
		-- 1.3.6.1.4.1.47477.10.21.8.3.10
		link8_R2AlarmPower OBJECT-TYPE
			SYNTAX DisplayString
			MAX-ACCESS read-write
			STATUS current
			DESCRIPTION
				"get or set the power alarm threshold of R2 in link8."
			::= { link8OBP 10 }


--  1.3.6.1.4.1.47477.10.21.8.3.29
		-- 1.3.6.1.4.1.47477.10.21.8.3.29
		link8_R3AlarmPower OBJECT-TYPE
			SYNTAX DisplayString
			MAX-ACCESS read-write
			STATUS current
			DESCRIPTION
				"get or set the power alarm threshold of R3 in link8."
			::= { link8OBP 29 }

		
--  1.3.6.1.4.1.47477.10.21.8.3.30
		-- 1.3.6.1.4.1.47477.10.21.8.3.30
		link8_R4AlarmPower OBJECT-TYPE
			SYNTAX DisplayString
			MAX-ACCESS read-write
			STATUS current
			DESCRIPTION
				"get or set the power alarm threshold of R4 in link8."
			::= { link8OBP 30 }

-- OBP4
--  1.3.6.1.4.1.47477.10.21.8.3.37
		-- 1.3.6.1.4.1.47477.10.21.8.3.37
		link8_1R1Power OBJECT-TYPE
			SYNTAX DisplayString
			MAX-ACCESS read-only
			STATUS current
			DESCRIPTION
				"get the power of 1R1 in link8."
			::= { link8OBP 37 }
			
--  1.3.6.1.4.1.47477.10.21.8.3.38
		-- 1.3.6.1.4.1.47477.10.21.8.3.38
		link8_1R2Power OBJECT-TYPE
			SYNTAX DisplayString
			MAX-ACCESS read-only
			STATUS current
			DESCRIPTION
				"get the power of 1R2 in link8."
			::= { link8OBP 38 }

--  1.3.6.1.4.1.47477.10.21.8.3.39
		-- 1.3.6.1.4.1.47477.10.21.8.3.39
		link8_1R3Power OBJECT-TYPE
			SYNTAX DisplayString
			MAX-ACCESS read-only
			STATUS current
			DESCRIPTION
				"get the power of 1R3 in link8."
			::= { link8OBP 39 }
			
--  1.3.6.1.4.1.47477.10.21.8.3.40
		-- 1.3.6.1.4.1.47477.10.21.8.3.40
		link8_1R4Power OBJECT-TYPE
			SYNTAX DisplayString
			MAX-ACCESS read-only
			STATUS current
			DESCRIPTION
				"get the power of 1R4 in link8."
			::= { link8OBP 40 }

--  1.3.6.1.4.1.47477.10.21.8.3.41
		-- 1.3.6.1.4.1.47477.10.21.8.3.41
		link8_2R1Power OBJECT-TYPE
			SYNTAX DisplayString
			MAX-ACCESS read-only
			STATUS current
			DESCRIPTION
				"get the power of 2R1 in link8."
			::= { link8OBP 41 }
			
--  1.3.6.1.4.1.47477.10.21.8.3.42
		-- 1.3.6.1.4.1.47477.10.21.8.3.42
		link8_2R2Power OBJECT-TYPE
			SYNTAX DisplayString
			MAX-ACCESS read-only
			STATUS current
			DESCRIPTION
				"get the power of 2R2 in link8."
			::= { link8OBP 42 }

--  1.3.6.1.4.1.47477.10.21.8.3.41
		-- 1.3.6.1.4.1.47477.10.21.8.3.43
		link8_2R3Power OBJECT-TYPE
			SYNTAX DisplayString
			MAX-ACCESS read-only
			STATUS current
			DESCRIPTION
				"get the power of 2R3 in link8."
			::= { link8OBP 43 }
			
--  1.3.6.1.4.1.47477.10.21.8.3.42
		-- 1.3.6.1.4.1.47477.10.21.8.3.44
		link8_2R4Power OBJECT-TYPE
			SYNTAX DisplayString
			MAX-ACCESS read-only
			STATUS current
			DESCRIPTION
				"get the power of 2R4 in link8."
			::= { link8OBP 44 }
			
--  1.3.6.1.4.1.47477.10.21.8.3.49
		-- 1.3.6.1.4.1.47477.10.21.8.3.49
		link8_1R1Wave OBJECT-TYPE
			SYNTAX INTEGER
				{
				w850nm(0),
				na(2)
				}
			MAX-ACCESS read-only
			STATUS current
			DESCRIPTION
				"get the wave length of 1R1 in link8."
			::= { link8OBP 49 }
		
--  1.3.6.1.4.1.47477.10.21.8.3.60
		-- 1.3.6.1.4.1.47477.10.21.8.3.60
		link8_1R2Wave OBJECT-TYPE
			SYNTAX INTEGER
				{
				w850nm(0),
				na(2)
				}
			MAX-ACCESS read-only
			STATUS current
			DESCRIPTION
				"get the wave length of 1R2 in link8."
			::= { link8OBP 60 }

--  1.3.6.1.4.1.47477.10.21.8.3.61
		-- 1.3.6.1.4.1.47477.10.21.8.3.61
		link8_1R3Wave OBJECT-TYPE
			SYNTAX INTEGER
				{
				w850nm(0),
				na(2)
				}
			MAX-ACCESS read-only
			STATUS current
			DESCRIPTION
				"get the wave length of 1R3 in link8."
			::= { link8OBP 61 }

		
--  1.3.6.1.4.1.47477.10.21.8.3.62
		-- 1.3.6.1.4.1.47477.10.21.8.3.62
		link8_1R4Wave OBJECT-TYPE
			SYNTAX INTEGER
				{
				w850nm(0),
				na(2)
				}
			MAX-ACCESS read-only
			STATUS current
			DESCRIPTION
				"get the wave length of 1R4 in link8."
			::= { link8OBP 62 }
	
--  1.3.6.1.4.1.47477.10.21.8.3.63
		-- 1.3.6.1.4.1.47477.10.21.8.3.63
		link8_2R1Wave OBJECT-TYPE
			SYNTAX INTEGER
				{
				w850nm(0),
				na(2)
				}
			MAX-ACCESS read-only
			STATUS current
			DESCRIPTION
				"get the wave length of 2R1 in link8."
			::= { link8OBP 63 }

		
--  1.3.6.1.4.1.47477.10.21.8.3.64
		-- 1.3.6.1.4.1.47477.10.21.8.3.64
		link8_2R2Wave OBJECT-TYPE
			SYNTAX INTEGER
				{
				w850nm(0),
				na(2)
				}
			MAX-ACCESS read-only
			STATUS current
			DESCRIPTION
				"get the wave length of 2R2 in link8."
			::= { link8OBP 64 }	
	
--  1.3.6.1.4.1.47477.10.21.8.3.65
		-- 1.3.6.1.4.1.47477.10.21.8.3.65
		link8_2R3Wave OBJECT-TYPE
			SYNTAX INTEGER
				{
				w850nm(0),
				na(2)
				}
			MAX-ACCESS read-only
			STATUS current
			DESCRIPTION
				"get the wave length of 2R3 in link8."
			::= { link8OBP 65 }

		
--  1.3.6.1.4.1.47477.10.21.8.3.66
		-- 1.3.6.1.4.1.47477.10.21.8.3.66
		link8_2R4Wave OBJECT-TYPE
			SYNTAX INTEGER
				{
				w850nm(0),
				na(2)
				}
			MAX-ACCESS read-only
			STATUS current
			DESCRIPTION
				"get the wave length of 2R4 in link8."
			::= { link8OBP 66 }	
			
--  1.3.6.1.4.1.47477.10.21.8.3.31
		-- 1.3.6.1.4.1.47477.10.21.8.3.31
		link8_1R1AlarmPower OBJECT-TYPE
			SYNTAX DisplayString
			MAX-ACCESS read-write
			STATUS current
			DESCRIPTION
				"get or set the power alarm threshold of 1R1 in link8."
			::= { link8OBP 31 }
			
--  1.3.6.1.4.1.47477.10.21.8.3.32
		-- 1.3.6.1.4.1.47477.10.21.8.3.32
		link8_1R2AlarmPower OBJECT-TYPE
			SYNTAX DisplayString
			MAX-ACCESS read-write
			STATUS current
			DESCRIPTION
				"get or set the power alarm threshold of 1R2 in link8."
			::= { link8OBP 32 }

--  1.3.6.1.4.1.47477.10.21.8.3.33
		-- 1.3.6.1.4.1.47477.10.21.8.3.33
		link8_1R3AlarmPower OBJECT-TYPE
			SYNTAX DisplayString
			MAX-ACCESS read-write
			STATUS current
			DESCRIPTION
				"get or set the power alarm threshold of 1R3 in link8."
			::= { link8OBP 33 }
			
--  1.3.6.1.4.1.47477.10.21.8.3.34
		-- 1.3.6.1.4.1.47477.10.21.8.3.34
		link8_1R4AlarmPower OBJECT-TYPE
			SYNTAX DisplayString
			MAX-ACCESS read-write
			STATUS current
			DESCRIPTION
				"get or set the power alarm threshold of 1R4 in link8."
			::= { link8OBP 34 }

--  1.3.6.1.4.1.47477.10.21.8.3.45
		-- 1.3.6.1.4.1.47477.10.21.8.3.45
		link8_2R1AlarmPower OBJECT-TYPE
			SYNTAX DisplayString
			MAX-ACCESS read-write
			STATUS current
			DESCRIPTION
				"get or set the power alarm threshold of 2R1 in link8."
			::= { link8OBP 45 }
			
--  1.3.6.1.4.1.47477.10.21.8.3.46
		-- 1.3.6.1.4.1.47477.10.21.8.3.46
		link8_2R2AlarmPower OBJECT-TYPE
			SYNTAX DisplayString
			MAX-ACCESS read-write
			STATUS current
			DESCRIPTION
				"get or set the power alarm threshold of 2R2 in link8."
			::= { link8OBP 46 }

--  1.3.6.1.4.1.47477.10.21.8.3.47
		-- 1.3.6.1.4.1.47477.10.21.8.3.47
		link8_2R3AlarmPower OBJECT-TYPE
			SYNTAX DisplayString
			MAX-ACCESS read-write
			STATUS current
			DESCRIPTION
				"get or set the power alarm threshold of 2R3 in link8."
			::= { link8OBP 47 }
			
--  1.3.6.1.4.1.47477.10.21.8.3.48
		-- 1.3.6.1.4.1.47477.10.21.8.3.48
		link8_2R4AlarmPower OBJECT-TYPE
			SYNTAX DisplayString
			MAX-ACCESS read-write
			STATUS current
			DESCRIPTION
				"get or set the power alarm threshold of 2R4 in link8."
			::= { link8OBP 48 }
			
--  1.3.6.1.4.1.47477.10.21.8.3.11
		-- 1.3.6.1.4.1.47477.10.21.8.3.11
		link8_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link8OBP 11 }
			
--  1.3.6.1.4.1.47477.10.21.8.3.67
		-- 1.3.6.1.4.1.47477.10.21.8.3.67
		link8_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link8OBP 67 }
			
--  1.3.6.1.4.1.47477.10.21.8.3.68
		-- 1.3.6.1.4.1.47477.10.21.8.3.68
		link8_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link8OBP 68 }
			
--  1.3.6.1.4.1.47477.10.21.8.3.12
		-- 1.3.6.1.4.1.47477.10.21.8.3.12
		link8_ReturnDelay OBJECT-TYPE
			--SYNTAX Integer32
			SYNTAX Integer32
			MAX-ACCESS read-write
			STATUS current
			DESCRIPTION
				"get or set how long link8 takes to return to automatic mode."
			::= { link8OBP 12 }
			
--  1.3.6.1.4.1.47477.10.21.8.3.13
		-- 1.3.6.1.4.1.47477.10.21.8.3.13
		link8_BackMode OBJECT-TYPE
			SYNTAX INTEGER
				{
				autoNoBack(0),
				autoBack(1)
				}
			MAX-ACCESS read-write
			STATUS current
			DESCRIPTION
				"get or set the back mode of link8."
			::= { link8OBP 13 }

		
--  1.3.6.1.4.1.47477.10.21.8.3.14
		-- 1.3.6.1.4.1.47477.10.21.8.3.14
		link8_BackDelay OBJECT-TYPE
			SYNTAX Integer32
			MAX-ACCESS read-write
			STATUS current
			DESCRIPTION
				"get or set the back delay."
			::= { link8OBP 14 }

--  1.3.6.1.4.1.47477.10.21.8.3.15
		-- 1.3.6.1.4.1.47477.10.21.8.3.15
		link8_ActiveHeartSwitch OBJECT-TYPE
			SYNTAX INTEGER
				{
				off(0),
				on(1)
				}
			MAX-ACCESS read-write
			STATUS current
			DESCRIPTION
				"get or set the switch status of active heartbeat."
			::= { link8OBP 15 }

		
--  1.3.6.1.4.1.47477.10.21.8.3.16
		-- 1.3.6.1.4.1.47477.10.21.8.3.16
		link8_ActiveSendInterval OBJECT-TYPE
			SYNTAX Integer32
			MAX-ACCESS read-write
			STATUS current
			DESCRIPTION
				"get or set the send interval of active heartbeat."
			::= { link8OBP 16 }		

--  1.3.6.1.4.1.47477.10.21.8.3.17
		-- 1.3.6.1.4.1.47477.10.21.8.3.17
		link8_ActiveTimeOut OBJECT-TYPE
			SYNTAX Integer32
			MAX-ACCESS read-write
			STATUS current
			DESCRIPTION
				"get or set how long the active heartbeat send timeout."
			::= { link8OBP 17 }

--  1.3.6.1.4.1.47477.10.21.8.3.18
		-- 1.3.6.1.4.1.47477.10.21.8.3.18
		link8_ActiveLossBypass OBJECT-TYPE
			SYNTAX Integer32
			MAX-ACCESS read-write
			STATUS current
			DESCRIPTION
				"get or set the bypass for active heartbeat packet loss."
			::= { link8OBP 18 }

--  1.3.6.1.4.1.47477.10.21.8.3.19
		-- 1.3.6.1.4.1.47477.10.21.8.3.19
		link8_PingIpAddress OBJECT-TYPE
			SYNTAX IpAddress
			MAX-ACCESS read-write
			STATUS current
			DESCRIPTION
				"get or set the ping ip address of link8."
			::= { link8OBP 19 }

--  1.3.6.1.4.1.47477.10.21.8.3.20
		-- 1.3.6.1.4.1.47477.10.21.8.3.20
		link8_PassiveHeartSwitch OBJECT-TYPE
			SYNTAX INTEGER
				{
				off(0),
				on(1)
				}
			MAX-ACCESS read-write
			STATUS current
			DESCRIPTION
				"get or set the switch status of passive heartbeat."
			::= { link8OBP 20 }
	

--  1.3.6.1.4.1.47477.10.21.8.3.21
		-- 1.3.6.1.4.1.47477.10.21.8.3.21
		link8_PassiveTimeOut OBJECT-TYPE
			SYNTAX Integer32
			MAX-ACCESS read-write
			STATUS current
			DESCRIPTION
				"get or set how long the passive heartbeat send timeout."
			::= { link8OBP 21 }

--  1.3.6.1.4.1.47477.10.21.8.3.22
		-- 1.3.6.1.4.1.47477.10.21.8.3.22
		link8_PassiveLossBypass OBJECT-TYPE
			SYNTAX Integer32
			MAX-ACCESS read-write
			STATUS current
			DESCRIPTION
				"get or set the bypass for passive heartbeat packet loss."
			::= { link8OBP 22 }

--  1.3.6.1.4.1.47477.10.21.8.3.23
		-- 1.3.6.1.4.1.47477.10.21.8.3.23
		link8_SwitchProtect OBJECT-TYPE
			SYNTAX INTEGER
				{
				off(0),
				on(1)
				}
			MAX-ACCESS read-write
			STATUS current
			DESCRIPTION
				"get or set the switch protection status of link8."
			::= { link8OBP 23 }
			
--  1.3.6.1.4.1.47477.10.21.8.3.24
		-- 1.3.6.1.4.1.47477.10.21.8.3.24
		link8_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link8OBP 24 }		

--  1.3.6.1.4.1.47477.10.21.8.3.25
		-- 1.3.6.1.4.1.47477.10.21.8.3.25
		link8_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link8OBP 25 }	

--  1.3.6.1.4.1.47477.10.21.8.3.26
		-- 1.3.6.1.4.1.47477.10.21.8.3.26
		link8_PowerAlarmStatus OBJECT-TYPE
			SYNTAX INTEGER
				{
				off(0),
				alarm(1),
				normal(2),
				na(3)
				}
			MAX-ACCESS read-only
			STATUS current
			DESCRIPTION
				"get whether a power alarm is generated."
			::= { link8OBP 26 }	


-- 1.3.6.1.4.1.47477.10.21.8.3.50.1
	link8_WorkModeChange 	OBJECT-TYPE    
    SYNTAX INTEGER	{
				manualMode(0),
				autoMode(1)
		}
	MAX-ACCESS read-only
	STATUS current
    DESCRIPTION
        "The Link mode Changed."
    ::= {link8OBPTrap 1}

-- 1.3.6.1.4.1.47477.10.21.8.3.50.2
	link8_StateChange 	OBJECT-TYPE    
    SYNTAX INTEGER	{
				bypass(0),
				primary(1)
		}
	MAX-ACCESS read-only
	STATUS current
    DESCRIPTION
        "The Link State(Channel) Changed."
    ::= {link8OBPTrap 2}

-- 1.3.6.1.4.1.47477.10.21.8.3.50.3
	link8_R1WaveSet 	OBJECT-TYPE    
    SYNTAX INTEGER	{
				w1310nm(0),
				w1550nm(1)
		}
	MAX-ACCESS read-only
	STATUS current
    DESCRIPTION
        "Set The link8 R1 Wave."
    ::= {link8OBPTrap 3}

-- 1.3.6.1.4.1.47477.10.21.8.3.50.4
	link8_R2WaveSet 	OBJECT-TYPE    
    SYNTAX INTEGER	{
				w1310nm(0),
				w1550nm(1)
		}
	MAX-ACCESS read-only
	STATUS current
    DESCRIPTION
        "Set The link8 R2 Wave."
    ::= {link8OBPTrap 4}			

-- 1.3.6.1.4.1.47477.10.21.8.3.50.5
	link8_R3WaveSet 	OBJECT-TYPE    
    SYNTAX INTEGER	{
				w1310nm(0),
				w1550nm(1)
		}
	MAX-ACCESS read-only
	STATUS current
    DESCRIPTION
        "Set The link8 R3 Wave."
    ::= {link8OBPTrap 5}

-- 1.3.6.1.4.1.47477.10.21.8.3.50.6
	link8_R4WaveSet 	OBJECT-TYPE    
    SYNTAX INTEGER	{
				w1310nm(0),
				w1550nm(1)
		}
	MAX-ACCESS read-only
	STATUS current
    DESCRIPTION
        "Set The link8 R4 Wave."
    ::= {link8OBPTrap 6}	
	
-- 1.3.6.1.4.1.47477.10.21.8.3.50.7
	link8_R1AlarmSet 	OBJECT-TYPE    
    SYNTAX DisplayString
	MAX-ACCESS read-only
	STATUS current
    DESCRIPTION
        "Set The link8 R1 Alarm Threshold."
    ::= {link8OBPTrap 7}

-- 1.3.6.1.4.1.47477.10.21.8.3.50.8
	link8_R2AlarmSet 	OBJECT-TYPE    
    SYNTAX DisplayString
	MAX-ACCESS read-only
	STATUS current
    DESCRIPTION
        "Set The link8 R2 Alarm Threshold."
    ::= {link8OBPTrap 8}
	
-- 1.3.6.1.4.1.47477.10.21.8.3.50.9
	link8_R3AlarmSet 	OBJECT-TYPE    
    SYNTAX DisplayString
	MAX-ACCESS read-only
	STATUS current
    DESCRIPTION
        "Set The link8 R3 Alarm Threshold."
    ::= {link8OBPTrap 9}

-- 1.3.6.1.4.1.47477.10.21.8.3.50.10
	link8_R4AlarmSet 	OBJECT-TYPE    
    SYNTAX DisplayString
	MAX-ACCESS read-only
	STATUS current
    DESCRIPTION
        "Set The link8 R4 Alarm Threshold."
    ::= {link8OBPTrap 10}	
	
	
-- 1.3.6.1.4.1.47477.10.21.8.3.50.11
	link8_1R1AlarmSet 	OBJECT-TYPE    
    SYNTAX DisplayString
	MAX-ACCESS read-only
	STATUS current
    DESCRIPTION
        "Set The link8 1R1 Alarm Threshold."
    ::= {link8OBPTrap 11}

-- 1.3.6.1.4.1.47477.10.21.8.3.50.12
	link8_2R1AlarmSet 	OBJECT-TYPE    
    SYNTAX DisplayString
	MAX-ACCESS read-only
	STATUS current
    DESCRIPTION
        "Set The link8 2R1 Alarm Threshold."
    ::= {link8OBPTrap 12}
	
-- 1.3.6.1.4.1.47477.10.21.8.3.50.13
	link8_1R2AlarmSet 	OBJECT-TYPE    
    SYNTAX DisplayString
	MAX-ACCESS read-only
	STATUS current
    DESCRIPTION
        "Set The link8 1R2 Alarm Threshold."
    ::= {link8OBPTrap 13}

-- 1.3.6.1.4.1.47477.10.21.8.3.50.14
	link8_2R2AlarmSet 	OBJECT-TYPE    
    SYNTAX DisplayString
	MAX-ACCESS read-only
	STATUS current
    DESCRIPTION
        "Set The link8 2R2 Alarm Threshold."
    ::= {link8OBPTrap 14}
	
-- 1.3.6.1.4.1.47477.10.21.8.3.50.15
	link8_1R3AlarmSet 	OBJECT-TYPE    
    SYNTAX DisplayString
	MAX-ACCESS read-only
	STATUS current
    DESCRIPTION
        "Set The link8 1R3 Alarm Threshold."
    ::= {link8OBPTrap 15}

-- 1.3.6.1.4.1.47477.10.21.8.3.50.16
	link8_2R3AlarmSet 	OBJECT-TYPE    
    SYNTAX DisplayString
	MAX-ACCESS read-only
	STATUS current
    DESCRIPTION
        "Set The link8 2R3 Alarm Threshold."
    ::= {link8OBPTrap 16}
	
-- 1.3.6.1.4.1.47477.10.21.8.3.50.17
	link8_1R4AlarmSet 	OBJECT-TYPE    
    SYNTAX DisplayString
	MAX-ACCESS read-only
	STATUS current
    DESCRIPTION
        "Set The link8 1R4 Alarm Threshold."
    ::= {link8OBPTrap 17}

-- 1.3.6.1.4.1.47477.10.21.8.3.50.18
	link8_2R4AlarmSet 	OBJECT-TYPE    
    SYNTAX DisplayString
	MAX-ACCESS read-only
	STATUS current
    DESCRIPTION
        "Set The link8 2R4 Alarm Threshold."
    ::= {link8OBPTrap 18}
	
-- 1.3.6.1.4.1.47477.10.21.8.3.50.19
	link8_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link8 PowerAlarmBypass2 Changed."
    ::= {link8OBPTrap 19}
	
-- 1.3.6.1.4.1.47477.10.21.8.3.50.20
	link8_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link8 PowerAlarmBypass4 Changed."
    ::= {link8OBPTrap 20}	
	
-- 1.3.6.1.4.1.47477.10.21.8.3.50.21
	link8_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link8 PowerAlarmBypass8 Changed."
    ::= {link8OBPTrap 21}
	
-- 1.3.6.1.4.1.47477.10.21.8.3.50.22
	link8_powerAlarmR1 	OBJECT-TYPE    
    SYNTAX DisplayString
	MAX-ACCESS read-only
	STATUS current
    DESCRIPTION
        "Set The link8 R1 Power Status Alarm."
    ::= {link8OBPTrap 22}
	
-- 1.3.6.1.4.1.47477.10.21.8.3.50.23
	link8_powerAlarmR2 	OBJECT-TYPE    
    SYNTAX DisplayString
	MAX-ACCESS read-only
	STATUS current
    DESCRIPTION
        "Set The link8 R2 Power Status Alarm."
    ::= {link8OBPTrap 23}
	
-- 1.3.6.1.4.1.47477.10.21.8.3.50.24
	link8_powerAlarmR3 	OBJECT-TYPE    
    SYNTAX DisplayString
	MAX-ACCESS read-only
	STATUS current
    DESCRIPTION
        "Set The link8 R3 Power Status Alarm."
    ::= {link8OBPTrap 24}
	
-- 1.3.6.1.4.1.47477.10.21.8.3.50.25
	link8_powerAlarmR4 	OBJECT-TYPE    
    SYNTAX DisplayString
	MAX-ACCESS read-only
	STATUS current
    DESCRIPTION
        "Set The link8 R4 Power Status Alarm."
    ::= {link8OBPTrap 25}
	
	
-- 1.3.6.1.4.1.47477.10.21.8.3.50.26
	link8_powerAlarm1R1 	OBJECT-TYPE    
    SYNTAX DisplayString
	MAX-ACCESS read-only
	STATUS current
    DESCRIPTION
        "Set The link8 1R1 Power Status Alarm."
    ::= {link8OBPTrap 26}
	
-- 1.3.6.1.4.1.47477.10.21.8.3.50.27
	link8_powerAlarm2R1 	OBJECT-TYPE    
    SYNTAX DisplayString
	MAX-ACCESS read-only
	STATUS current
    DESCRIPTION
        "Set The link8 2R1 Power Status Alarm."
    ::= {link8OBPTrap 27}
	
-- 1.3.6.1.4.1.47477.10.21.8.3.50.28
	link8_powerAlarm1R2 	OBJECT-TYPE    
    SYNTAX DisplayString
	MAX-ACCESS read-only
	STATUS current
    DESCRIPTION
        "Set The link8 1R2 Power Status Alarm."
    ::= {link8OBPTrap 28}
	
-- 1.3.6.1.4.1.47477.10.21.8.3.50.29
	link8_powerAlarm2R2 	OBJECT-TYPE    
    SYNTAX DisplayString
	MAX-ACCESS read-only
	STATUS current
    DESCRIPTION
        "Set The link8 2R2 Power Status Alarm."
    ::= {link8OBPTrap 29}
	
-- 1.3.6.1.4.1.47477.10.21.8.3.50.30
	link8_powerAlarm1R3 	OBJECT-TYPE    
    SYNTAX DisplayString
	MAX-ACCESS read-only
	STATUS current
    DESCRIPTION
        "Set The link8 1R3 Power Status Alarm."
    ::= {link8OBPTrap 30}
	
-- 1.3.6.1.4.1.47477.10.21.8.3.50.31
	link8_powerAlarm2R3 	OBJECT-TYPE    
    SYNTAX DisplayString
	MAX-ACCESS read-only
	STATUS current
    DESCRIPTION
        "Set The link8 2R1 Power Status Alarm."
    ::= {link8OBPTrap 31}
	
-- 1.3.6.1.4.1.47477.10.21.8.3.50.32
	link8_powerAlarm1R4 	OBJECT-TYPE    
    SYNTAX DisplayString
	MAX-ACCESS read-only
	STATUS current
    DESCRIPTION
        "Set The link8 1R4 Power Status Alarm."
    ::= {link8OBPTrap 32}
	
-- 1.3.6.1.4.1.47477.10.21.8.3.50.33
	link8_powerAlarm2R4 	OBJECT-TYPE    
    SYNTAX DisplayString
	MAX-ACCESS read-only
	STATUS current
    DESCRIPTION
        "Set The link8 2R4 Power Status Alarm."
    ::= {link8OBPTrap 33}
	
--  1.3.6.1.4.1.47477.10.21.9.3.1
		-- 1.3.6.1.4.1.47477.10.21.9.3.1
		link9_State OBJECT-TYPE
			SYNTAX INTEGER
				{
				off(0),
				on(1)
				}
			MAX-ACCESS read-only
			STATUS current
			DESCRIPTION
				"get the information about whether link9 is working."
			::= { link9OBP 1 }

		
--  1.3.6.1.4.1.47477.10.21.9.3.2
		-- 1.3.6.1.4.1.47477.10.21.9.3.2
		link9_DeviceType OBJECT-TYPE
			SYNTAX DisplayString
			MAX-ACCESS read-only
			STATUS current
			DESCRIPTION
				"get the type of card in link9."
			::= { link9OBP 2 }

			
--  1.3.6.1.4.1.47477.10.21.9.3.3
		-- 1.3.6.1.4.1.47477.10.21.9.3.3
		link9_WorkMode OBJECT-TYPE
			SYNTAX INTEGER
				{
				manualMode(0),
				autoMode(1)
				}
			MAX-ACCESS read-write
			STATUS current
			DESCRIPTION
				"get or set link9's work mode."
			::= { link9OBP 3 }

		
--  1.3.6.1.4.1.47477.10.21.9.3.4
		-- 1.3.6.1.4.1.47477.10.21.9.3.4
		link9_Channel OBJECT-TYPE
			SYNTAX INTEGER
				{
				bypass(0),
				primary(1)
				}
			MAX-ACCESS read-write
			STATUS current
			DESCRIPTION
				"get or set the channel in which link9 works."
			::= { link9OBP 4 }


--  1.3.6.1.4.1.47477.10.21.9.3.5
		-- 1.3.6.1.4.1.47477.10.21.9.3.5
		link9_R1Power OBJECT-TYPE
			SYNTAX DisplayString
			MAX-ACCESS read-only
			STATUS current
			DESCRIPTION
				"get the power of R1 in link9."
			::= { link9OBP 5 }

		
--  1.3.6.1.4.1.47477.10.21.9.3.6
		-- 1.3.6.1.4.1.47477.10.21.9.3.6
		link9_R2Power OBJECT-TYPE
			SYNTAX DisplayString
			MAX-ACCESS read-only
			STATUS current
			DESCRIPTION
				"get the power of R2 in link9."
			::= { link9OBP 6 }
			
--  1.3.6.1.4.1.47477.10.21.9.3.35
		-- 1.3.6.1.4.1.47477.10.21.9.3.35
		link9_R3Power OBJECT-TYPE
			SYNTAX DisplayString
			MAX-ACCESS read-only
			STATUS current
			DESCRIPTION
				"get the power of R3 in link9."
			::= { link9OBP 35 }
			
--  1.3.6.1.4.1.47477.10.21.9.3.36
		-- 1.3.6.1.4.1.47477.10.21.9.3.36
		link9_R4Power OBJECT-TYPE
			SYNTAX DisplayString
			MAX-ACCESS read-only
			STATUS current
			DESCRIPTION
				"get the power of R4 in link9."
			::= { link9OBP 36 }		
		
--  1.3.6.1.4.1.47477.10.21.9.3.7
		-- 1.3.6.1.4.1.47477.10.21.9.3.7
		link9_R1Wave OBJECT-TYPE
			SYNTAX INTEGER
				{
				w1310nm(0),
				w1550nm(1),
				na(2)
				}
			MAX-ACCESS read-write
			STATUS current
			DESCRIPTION
				"get or set the wave length of R1 in link9."
			::= { link9OBP 7 }

		
--  1.3.6.1.4.1.47477.10.21.9.3.8
		-- 1.3.6.1.4.1.47477.10.21.9.3.8
		link9_R2Wave OBJECT-TYPE
			SYNTAX INTEGER
				{
				w1310nm(0),
				w1550nm(1),
				na(2)
				}
			MAX-ACCESS read-write
			STATUS current
			DESCRIPTION
				"get or set the wave length of R2 in link9."
			::= { link9OBP 8 }


--  1.3.6.1.4.1.47477.10.21.9.3.27
		-- 1.3.6.1.4.1.47477.10.21.9.3.27
		link9_R3Wave OBJECT-TYPE
			SYNTAX INTEGER
				{
				w1310nm(0),
				w1550nm(1),
				na(2)
				}
			MAX-ACCESS read-write
			STATUS current
			DESCRIPTION
				"get or set the wave length of R3 in link9."
			::= { link9OBP 27 }

		
--  1.3.6.1.4.1.47477.10.21.9.3.28
		-- 1.3.6.1.4.1.47477.10.21.9.3.28
		link9_R4Wave OBJECT-TYPE
			SYNTAX INTEGER
				{
				w1310nm(0),
				w1550nm(1),
				na(2)
				}
			MAX-ACCESS read-write
			STATUS current
			DESCRIPTION
				"get or set the wave length of R4 in link9."
			::= { link9OBP 28 }
			
--  1.3.6.1.4.1.47477.10.21.9.3.9
		-- 1.3.6.1.4.1.47477.10.21.9.3.9
		link9_R1AlarmPower OBJECT-TYPE
			SYNTAX DisplayString
			MAX-ACCESS read-write
			STATUS current
			DESCRIPTION
				"get or set the power alarm threshold of R1 in link9."
			::= { link9OBP 9 }

		
--  1.3.6.1.4.1.47477.10.21.9.3.10
		-- 1.3.6.1.4.1.47477.10.21.9.3.10
		link9_R2AlarmPower OBJECT-TYPE
			SYNTAX DisplayString
			MAX-ACCESS read-write
			STATUS current
			DESCRIPTION
				"get or set the power alarm threshold of R2 in link9."
			::= { link9OBP 10 }


--  1.3.6.1.4.1.47477.10.21.9.3.29
		-- 1.3.6.1.4.1.47477.10.21.9.3.29
		link9_R3AlarmPower OBJECT-TYPE
			SYNTAX DisplayString
			MAX-ACCESS read-write
			STATUS current
			DESCRIPTION
				"get or set the power alarm threshold of R3 in link9."
			::= { link9OBP 29 }

		
--  1.3.6.1.4.1.47477.10.21.9.3.30
		-- 1.3.6.1.4.1.47477.10.21.9.3.30
		link9_R4AlarmPower OBJECT-TYPE
			SYNTAX DisplayString
			MAX-ACCESS read-write
			STATUS current
			DESCRIPTION
				"get or set the power alarm threshold of R4 in link9."
			::= { link9OBP 30 }

-- OBP4
--  1.3.6.1.4.1.47477.10.21.9.3.37
		-- 1.3.6.1.4.1.47477.10.21.9.3.37
		link9_1R1Power OBJECT-TYPE
			SYNTAX DisplayString
			MAX-ACCESS read-only
			STATUS current
			DESCRIPTION
				"get the power of 1R1 in link9."
			::= { link9OBP 37 }
			
--  1.3.6.1.4.1.47477.10.21.9.3.38
		-- 1.3.6.1.4.1.47477.10.21.9.3.38
		link9_1R2Power OBJECT-TYPE
			SYNTAX DisplayString
			MAX-ACCESS read-only
			STATUS current
			DESCRIPTION
				"get the power of 1R2 in link9."
			::= { link9OBP 38 }

--  1.3.6.1.4.1.47477.10.21.9.3.39
		-- 1.3.6.1.4.1.47477.10.21.9.3.39
		link9_1R3Power OBJECT-TYPE
			SYNTAX DisplayString
			MAX-ACCESS read-only
			STATUS current
			DESCRIPTION
				"get the power of 1R3 in link9."
			::= { link9OBP 39 }
			
--  1.3.6.1.4.1.47477.10.21.9.3.40
		-- 1.3.6.1.4.1.47477.10.21.9.3.40
		link9_1R4Power OBJECT-TYPE
			SYNTAX DisplayString
			MAX-ACCESS read-only
			STATUS current
			DESCRIPTION
				"get the power of 1R4 in link9."
			::= { link9OBP 40 }

--  1.3.6.1.4.1.47477.10.21.9.3.41
		-- 1.3.6.1.4.1.47477.10.21.9.3.41
		link9_2R1Power OBJECT-TYPE
			SYNTAX DisplayString
			MAX-ACCESS read-only
			STATUS current
			DESCRIPTION
				"get the power of 2R1 in link9."
			::= { link9OBP 41 }
			
--  1.3.6.1.4.1.47477.10.21.9.3.42
		-- 1.3.6.1.4.1.47477.10.21.9.3.42
		link9_2R2Power OBJECT-TYPE
			SYNTAX DisplayString
			MAX-ACCESS read-only
			STATUS current
			DESCRIPTION
				"get the power of 2R2 in link9."
			::= { link9OBP 42 }

--  1.3.6.1.4.1.47477.10.21.9.3.41
		-- 1.3.6.1.4.1.47477.10.21.9.3.43
		link9_2R3Power OBJECT-TYPE
			SYNTAX DisplayString
			MAX-ACCESS read-only
			STATUS current
			DESCRIPTION
				"get the power of 2R3 in link9."
			::= { link9OBP 43 }
			
--  1.3.6.1.4.1.47477.10.21.9.3.42
		-- 1.3.6.1.4.1.47477.10.21.9.3.44
		link9_2R4Power OBJECT-TYPE
			SYNTAX DisplayString
			MAX-ACCESS read-only
			STATUS current
			DESCRIPTION
				"get the power of 2R4 in link9."
			::= { link9OBP 44 }
			
--  1.3.6.1.4.1.47477.10.21.9.3.49
		-- 1.3.6.1.4.1.47477.10.21.9.3.49
		link9_1R1Wave OBJECT-TYPE
			SYNTAX INTEGER
				{
				w850nm(0),
				na(2)
				}
			MAX-ACCESS read-only
			STATUS current
			DESCRIPTION
				"get the wave length of 1R1 in link9."
			::= { link9OBP 49 }
		
--  1.3.6.1.4.1.47477.10.21.9.3.60
		-- 1.3.6.1.4.1.47477.10.21.9.3.60
		link9_1R2Wave OBJECT-TYPE
			SYNTAX INTEGER
				{
				w850nm(0),
				na(2)
				}
			MAX-ACCESS read-only
			STATUS current
			DESCRIPTION
				"get the wave length of 1R2 in link9."
			::= { link9OBP 60 }

--  1.3.6.1.4.1.47477.10.21.9.3.61
		-- 1.3.6.1.4.1.47477.10.21.9.3.61
		link9_1R3Wave OBJECT-TYPE
			SYNTAX INTEGER
				{
				w850nm(0),
				na(2)
				}
			MAX-ACCESS read-only
			STATUS current
			DESCRIPTION
				"get the wave length of 1R3 in link9."
			::= { link9OBP 61 }

		
--  1.3.6.1.4.1.47477.10.21.9.3.62
		-- 1.3.6.1.4.1.47477.10.21.9.3.62
		link9_1R4Wave OBJECT-TYPE
			SYNTAX INTEGER
				{
				w850nm(0),
				na(2)
				}
			MAX-ACCESS read-only
			STATUS current
			DESCRIPTION
				"get the wave length of 1R4 in link9."
			::= { link9OBP 62 }
	
--  1.3.6.1.4.1.47477.10.21.9.3.63
		-- 1.3.6.1.4.1.47477.10.21.9.3.63
		link9_2R1Wave OBJECT-TYPE
			SYNTAX INTEGER
				{
				w850nm(0),
				na(2)
				}
			MAX-ACCESS read-only
			STATUS current
			DESCRIPTION
				"get the wave length of 2R1 in link9."
			::= { link9OBP 63 }

		
--  1.3.6.1.4.1.47477.10.21.9.3.64
		-- 1.3.6.1.4.1.47477.10.21.9.3.64
		link9_2R2Wave OBJECT-TYPE
			SYNTAX INTEGER
				{
				w850nm(0),
				na(2)
				}
			MAX-ACCESS read-only
			STATUS current
			DESCRIPTION
				"get the wave length of 2R2 in link9."
			::= { link9OBP 64 }	
	
--  1.3.6.1.4.1.47477.10.21.9.3.65
		-- 1.3.6.1.4.1.47477.10.21.9.3.65
		link9_2R3Wave OBJECT-TYPE
			SYNTAX INTEGER
				{
				w850nm(0),
				na(2)
				}
			MAX-ACCESS read-only
			STATUS current
			DESCRIPTION
				"get the wave length of 2R3 in link9."
			::= { link9OBP 65 }

		
--  1.3.6.1.4.1.47477.10.21.9.3.66
		-- 1.3.6.1.4.1.47477.10.21.9.3.66
		link9_2R4Wave OBJECT-TYPE
			SYNTAX INTEGER
				{
				w850nm(0),
				na(2)
				}
			MAX-ACCESS read-only
			STATUS current
			DESCRIPTION
				"get the wave length of 2R4 in link9."
			::= { link9OBP 66 }	
			
--  1.3.6.1.4.1.47477.10.21.9.3.31
		-- 1.3.6.1.4.1.47477.10.21.9.3.31
		link9_1R1AlarmPower OBJECT-TYPE
			SYNTAX DisplayString
			MAX-ACCESS read-write
			STATUS current
			DESCRIPTION
				"get or set the power alarm threshold of 1R1 in link9."
			::= { link9OBP 31 }
			
--  1.3.6.1.4.1.47477.10.21.9.3.32
		-- 1.3.6.1.4.1.47477.10.21.9.3.32
		link9_1R2AlarmPower OBJECT-TYPE
			SYNTAX DisplayString
			MAX-ACCESS read-write
			STATUS current
			DESCRIPTION
				"get or set the power alarm threshold of 1R2 in link9."
			::= { link9OBP 32 }

--  1.3.6.1.4.1.47477.10.21.9.3.33
		-- 1.3.6.1.4.1.47477.10.21.9.3.33
		link9_1R3AlarmPower OBJECT-TYPE
			SYNTAX DisplayString
			MAX-ACCESS read-write
			STATUS current
			DESCRIPTION
				"get or set the power alarm threshold of 1R3 in link9."
			::= { link9OBP 33 }
			
--  1.3.6.1.4.1.47477.10.21.9.3.34
		-- 1.3.6.1.4.1.47477.10.21.9.3.34
		link9_1R4AlarmPower OBJECT-TYPE
			SYNTAX DisplayString
			MAX-ACCESS read-write
			STATUS current
			DESCRIPTION
				"get or set the power alarm threshold of 1R4 in link9."
			::= { link9OBP 34 }

--  1.3.6.1.4.1.47477.10.21.9.3.45
		-- 1.3.6.1.4.1.47477.10.21.9.3.45
		link9_2R1AlarmPower OBJECT-TYPE
			SYNTAX DisplayString
			MAX-ACCESS read-write
			STATUS current
			DESCRIPTION
				"get or set the power alarm threshold of 2R1 in link9."
			::= { link9OBP 45 }
			
--  1.3.6.1.4.1.47477.10.21.9.3.46
		-- 1.3.6.1.4.1.47477.10.21.9.3.46
		link9_2R2AlarmPower OBJECT-TYPE
			SYNTAX DisplayString
			MAX-ACCESS read-write
			STATUS current
			DESCRIPTION
				"get or set the power alarm threshold of 2R2 in link9."
			::= { link9OBP 46 }

--  1.3.6.1.4.1.47477.10.21.9.3.47
		-- 1.3.6.1.4.1.47477.10.21.9.3.47
		link9_2R3AlarmPower OBJECT-TYPE
			SYNTAX DisplayString
			MAX-ACCESS read-write
			STATUS current
			DESCRIPTION
				"get or set the power alarm threshold of 2R3 in link9."
			::= { link9OBP 47 }
			
--  1.3.6.1.4.1.47477.10.21.9.3.48
		-- 1.3.6.1.4.1.47477.10.21.9.3.48
		link9_2R4AlarmPower OBJECT-TYPE
			SYNTAX DisplayString
			MAX-ACCESS read-write
			STATUS current
			DESCRIPTION
				"get or set the power alarm threshold of 2R4 in link9."
			::= { link9OBP 48 }
			
--  1.3.6.1.4.1.47477.10.21.9.3.11
		-- 1.3.6.1.4.1.47477.10.21.9.3.11
		link9_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link9OBP 11 }
			
--  1.3.6.1.4.1.47477.10.21.9.3.67
		-- 1.3.6.1.4.1.47477.10.21.9.3.67
		link9_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link9OBP 67 }
			
--  1.3.6.1.4.1.47477.10.21.9.3.68
		-- 1.3.6.1.4.1.47477.10.21.9.3.68
		link9_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link9OBP 68 }
			
--  1.3.6.1.4.1.47477.10.21.9.3.12
		-- 1.3.6.1.4.1.47477.10.21.9.3.12
		link9_ReturnDelay OBJECT-TYPE
			--SYNTAX Integer32
			SYNTAX Integer32
			MAX-ACCESS read-write
			STATUS current
			DESCRIPTION
				"get or set how long link9 takes to return to automatic mode."
			::= { link9OBP 12 }
			
--  1.3.6.1.4.1.47477.10.21.9.3.13
		-- 1.3.6.1.4.1.47477.10.21.9.3.13
		link9_BackMode OBJECT-TYPE
			SYNTAX INTEGER
				{
				autoNoBack(0),
				autoBack(1)
				}
			MAX-ACCESS read-write
			STATUS current
			DESCRIPTION
				"get or set the back mode of link9."
			::= { link9OBP 13 }

		
--  1.3.6.1.4.1.47477.10.21.9.3.14
		-- 1.3.6.1.4.1.47477.10.21.9.3.14
		link9_BackDelay OBJECT-TYPE
			SYNTAX Integer32
			MAX-ACCESS read-write
			STATUS current
			DESCRIPTION
				"get or set the back delay."
			::= { link9OBP 14 }

--  1.3.6.1.4.1.47477.10.21.9.3.15
		-- 1.3.6.1.4.1.47477.10.21.9.3.15
		link9_ActiveHeartSwitch OBJECT-TYPE
			SYNTAX INTEGER
				{
				off(0),
				on(1)
				}
			MAX-ACCESS read-write
			STATUS current
			DESCRIPTION
				"get or set the switch status of active heartbeat."
			::= { link9OBP 15 }

		
--  1.3.6.1.4.1.47477.10.21.9.3.16
		-- 1.3.6.1.4.1.47477.10.21.9.3.16
		link9_ActiveSendInterval OBJECT-TYPE
			SYNTAX Integer32
			MAX-ACCESS read-write
			STATUS current
			DESCRIPTION
				"get or set the send interval of active heartbeat."
			::= { link9OBP 16 }		

--  1.3.6.1.4.1.47477.10.21.9.3.17
		-- 1.3.6.1.4.1.47477.10.21.9.3.17
		link9_ActiveTimeOut OBJECT-TYPE
			SYNTAX Integer32
			MAX-ACCESS read-write
			STATUS current
			DESCRIPTION
				"get or set how long the active heartbeat send timeout."
			::= { link9OBP 17 }

--  1.3.6.1.4.1.47477.10.21.9.3.18
		-- 1.3.6.1.4.1.47477.10.21.9.3.18
		link9_ActiveLossBypass OBJECT-TYPE
			SYNTAX Integer32
			MAX-ACCESS read-write
			STATUS current
			DESCRIPTION
				"get or set the bypass for active heartbeat packet loss."
			::= { link9OBP 18 }

--  1.3.6.1.4.1.47477.10.21.9.3.19
		-- 1.3.6.1.4.1.47477.10.21.9.3.19
		link9_PingIpAddress OBJECT-TYPE
			SYNTAX IpAddress
			MAX-ACCESS read-write
			STATUS current
			DESCRIPTION
				"get or set the ping ip address of link9."
			::= { link9OBP 19 }

--  1.3.6.1.4.1.47477.10.21.9.3.20
		-- 1.3.6.1.4.1.47477.10.21.9.3.20
		link9_PassiveHeartSwitch OBJECT-TYPE
			SYNTAX INTEGER
				{
				off(0),
				on(1)
				}
			MAX-ACCESS read-write
			STATUS current
			DESCRIPTION
				"get or set the switch status of passive heartbeat."
			::= { link9OBP 20 }
	

--  1.3.6.1.4.1.47477.10.21.9.3.21
		-- 1.3.6.1.4.1.47477.10.21.9.3.21
		link9_PassiveTimeOut OBJECT-TYPE
			SYNTAX Integer32
			MAX-ACCESS read-write
			STATUS current
			DESCRIPTION
				"get or set how long the passive heartbeat send timeout."
			::= { link9OBP 21 }

--  1.3.6.1.4.1.47477.10.21.9.3.22
		-- 1.3.6.1.4.1.47477.10.21.9.3.22
		link9_PassiveLossBypass OBJECT-TYPE
			SYNTAX Integer32
			MAX-ACCESS read-write
			STATUS current
			DESCRIPTION
				"get or set the bypass for passive heartbeat packet loss."
			::= { link9OBP 22 }

--  1.3.6.1.4.1.47477.10.21.9.3.23
		-- 1.3.6.1.4.1.47477.10.21.9.3.23
		link9_SwitchProtect OBJECT-TYPE
			SYNTAX INTEGER
				{
				off(0),
				on(1)
				}
			MAX-ACCESS read-write
			STATUS current
			DESCRIPTION
				"get or set the switch protection status of link9."
			::= { link9OBP 23 }
			
--  1.3.6.1.4.1.47477.10.21.9.3.24
		-- 1.3.6.1.4.1.47477.10.21.9.3.24
		link9_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link9OBP 24 }		

--  1.3.6.1.4.1.47477.10.21.9.3.25
		-- 1.3.6.1.4.1.47477.10.21.9.3.25
		link9_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link9OBP 25 }	

--  1.3.6.1.4.1.47477.10.21.9.3.26
		-- 1.3.6.1.4.1.47477.10.21.9.3.26
		link9_PowerAlarmStatus OBJECT-TYPE
			SYNTAX INTEGER
				{
				off(0),
				alarm(1),
				normal(2),
				na(3)
				}
			MAX-ACCESS read-only
			STATUS current
			DESCRIPTION
				"get whether a power alarm is generated."
			::= { link9OBP 26 }	


-- 1.3.6.1.4.1.47477.10.21.9.3.50.1
	link9_WorkModeChange 	OBJECT-TYPE    
    SYNTAX INTEGER	{
				manualMode(0),
				autoMode(1)
		}
	MAX-ACCESS read-only
	STATUS current
    DESCRIPTION
        "The Link mode Changed."
    ::= {link9OBPTrap 1}

-- 1.3.6.1.4.1.47477.10.21.9.3.50.2
	link9_StateChange 	OBJECT-TYPE    
    SYNTAX INTEGER	{
				bypass(0),
				primary(1)
		}
	MAX-ACCESS read-only
	STATUS current
    DESCRIPTION
        "The Link State(Channel) Changed."
    ::= {link9OBPTrap 2}

-- 1.3.6.1.4.1.47477.10.21.9.3.50.3
	link9_R1WaveSet 	OBJECT-TYPE    
    SYNTAX INTEGER	{
				w1310nm(0),
				w1550nm(1)
		}
	MAX-ACCESS read-only
	STATUS current
    DESCRIPTION
        "Set The link9 R1 Wave."
    ::= {link9OBPTrap 3}

-- 1.3.6.1.4.1.47477.10.21.9.3.50.4
	link9_R2WaveSet 	OBJECT-TYPE    
    SYNTAX INTEGER	{
				w1310nm(0),
				w1550nm(1)
		}
	MAX-ACCESS read-only
	STATUS current
    DESCRIPTION
        "Set The link9 R2 Wave."
    ::= {link9OBPTrap 4}			

-- 1.3.6.1.4.1.47477.10.21.9.3.50.5
	link9_R3WaveSet 	OBJECT-TYPE    
    SYNTAX INTEGER	{
				w1310nm(0),
				w1550nm(1)
		}
	MAX-ACCESS read-only
	STATUS current
    DESCRIPTION
        "Set The link9 R3 Wave."
    ::= {link9OBPTrap 5}

-- 1.3.6.1.4.1.47477.10.21.9.3.50.6
	link9_R4WaveSet 	OBJECT-TYPE    
    SYNTAX INTEGER	{
				w1310nm(0),
				w1550nm(1)
		}
	MAX-ACCESS read-only
	STATUS current
    DESCRIPTION
        "Set The link9 R4 Wave."
    ::= {link9OBPTrap 6}	
	
-- 1.3.6.1.4.1.47477.10.21.9.3.50.7
	link9_R1AlarmSet 	OBJECT-TYPE    
    SYNTAX DisplayString
	MAX-ACCESS read-only
	STATUS current
    DESCRIPTION
        "Set The link9 R1 Alarm Threshold."
    ::= {link9OBPTrap 7}

-- 1.3.6.1.4.1.47477.10.21.9.3.50.8
	link9_R2AlarmSet 	OBJECT-TYPE    
    SYNTAX DisplayString
	MAX-ACCESS read-only
	STATUS current
    DESCRIPTION
        "Set The link9 R2 Alarm Threshold."
    ::= {link9OBPTrap 8}
	
-- 1.3.6.1.4.1.47477.10.21.9.3.50.9
	link9_R3AlarmSet 	OBJECT-TYPE    
    SYNTAX DisplayString
	MAX-ACCESS read-only
	STATUS current
    DESCRIPTION
        "Set The link9 R3 Alarm Threshold."
    ::= {link9OBPTrap 9}

-- 1.3.6.1.4.1.47477.10.21.9.3.50.10
	link9_R4AlarmSet 	OBJECT-TYPE    
    SYNTAX DisplayString
	MAX-ACCESS read-only
	STATUS current
    DESCRIPTION
        "Set The link9 R4 Alarm Threshold."
    ::= {link9OBPTrap 10}	
	
	
-- 1.3.6.1.4.1.47477.10.21.9.3.50.11
	link9_1R1AlarmSet 	OBJECT-TYPE    
    SYNTAX DisplayString
	MAX-ACCESS read-only
	STATUS current
    DESCRIPTION
        "Set The link9 1R1 Alarm Threshold."
    ::= {link9OBPTrap 11}

-- 1.3.6.1.4.1.47477.10.21.9.3.50.12
	link9_2R1AlarmSet 	OBJECT-TYPE    
    SYNTAX DisplayString
	MAX-ACCESS read-only
	STATUS current
    DESCRIPTION
        "Set The link9 2R1 Alarm Threshold."
    ::= {link9OBPTrap 12}
	
-- 1.3.6.1.4.1.47477.10.21.9.3.50.13
	link9_1R2AlarmSet 	OBJECT-TYPE    
    SYNTAX DisplayString
	MAX-ACCESS read-only
	STATUS current
    DESCRIPTION
        "Set The link9 1R2 Alarm Threshold."
    ::= {link9OBPTrap 13}

-- 1.3.6.1.4.1.47477.10.21.9.3.50.14
	link9_2R2AlarmSet 	OBJECT-TYPE    
    SYNTAX DisplayString
	MAX-ACCESS read-only
	STATUS current
    DESCRIPTION
        "Set The link9 2R2 Alarm Threshold."
    ::= {link9OBPTrap 14}
	
-- 1.3.6.1.4.1.47477.10.21.9.3.50.15
	link9_1R3AlarmSet 	OBJECT-TYPE    
    SYNTAX DisplayString
	MAX-ACCESS read-only
	STATUS current
    DESCRIPTION
        "Set The link9 1R3 Alarm Threshold."
    ::= {link9OBPTrap 15}

-- 1.3.6.1.4.1.47477.10.21.9.3.50.16
	link9_2R3AlarmSet 	OBJECT-TYPE    
    SYNTAX DisplayString
	MAX-ACCESS read-only
	STATUS current
    DESCRIPTION
        "Set The link9 2R3 Alarm Threshold."
    ::= {link9OBPTrap 16}
	
-- 1.3.6.1.4.1.47477.10.21.9.3.50.17
	link9_1R4AlarmSet 	OBJECT-TYPE    
    SYNTAX DisplayString
	MAX-ACCESS read-only
	STATUS current
    DESCRIPTION
        "Set The link9 1R4 Alarm Threshold."
    ::= {link9OBPTrap 17}

-- 1.3.6.1.4.1.47477.10.21.9.3.50.18
	link9_2R4AlarmSet 	OBJECT-TYPE    
    SYNTAX DisplayString
	MAX-ACCESS read-only
	STATUS current
    DESCRIPTION
        "Set The link9 2R4 Alarm Threshold."
    ::= {link9OBPTrap 18}
	
-- 1.3.6.1.4.1.47477.10.21.9.3.50.19
	link9_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link9 PowerAlarmBypass2 Changed."
    ::= {link9OBPTrap 19}
	
-- 1.3.6.1.4.1.47477.10.21.9.3.50.20
	link9_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link9 PowerAlarmBypass4 Changed."
    ::= {link9OBPTrap 20}	
	
-- 1.3.6.1.4.1.47477.10.21.9.3.50.21
	link9_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link9 PowerAlarmBypass8 Changed."
    ::= {link9OBPTrap 21}
	
-- 1.3.6.1.4.1.47477.10.21.9.3.50.22
	link9_powerAlarmR1 	OBJECT-TYPE    
    SYNTAX DisplayString
	MAX-ACCESS read-only
	STATUS current
    DESCRIPTION
        "Set The link9 R1 Power Status Alarm."
    ::= {link9OBPTrap 22}
	
-- 1.3.6.1.4.1.47477.10.21.9.3.50.23
	link9_powerAlarmR2 	OBJECT-TYPE    
    SYNTAX DisplayString
	MAX-ACCESS read-only
	STATUS current
    DESCRIPTION
        "Set The link9 R2 Power Status Alarm."
    ::= {link9OBPTrap 23}
	
-- 1.3.6.1.4.1.47477.10.21.9.3.50.24
	link9_powerAlarmR3 	OBJECT-TYPE    
    SYNTAX DisplayString
	MAX-ACCESS read-only
	STATUS current
    DESCRIPTION
        "Set The link9 R3 Power Status Alarm."
    ::= {link9OBPTrap 24}
	
-- 1.3.6.1.4.1.47477.10.21.9.3.50.25
	link9_powerAlarmR4 	OBJECT-TYPE    
    SYNTAX DisplayString
	MAX-ACCESS read-only
	STATUS current
    DESCRIPTION
        "Set The link9 R4 Power Status Alarm."
    ::= {link9OBPTrap 25}
	
	
-- 1.3.6.1.4.1.47477.10.21.9.3.50.26
	link9_powerAlarm1R1 	OBJECT-TYPE    
    SYNTAX DisplayString
	MAX-ACCESS read-only
	STATUS current
    DESCRIPTION
        "Set The link9 1R1 Power Status Alarm."
    ::= {link9OBPTrap 26}
	
-- 1.3.6.1.4.1.47477.10.21.9.3.50.27
	link9_powerAlarm2R1 	OBJECT-TYPE    
    SYNTAX DisplayString
	MAX-ACCESS read-only
	STATUS current
    DESCRIPTION
        "Set The link9 2R1 Power Status Alarm."
    ::= {link9OBPTrap 27}
	
-- 1.3.6.1.4.1.47477.10.21.9.3.50.28
	link9_powerAlarm1R2 	OBJECT-TYPE    
    SYNTAX DisplayString
	MAX-ACCESS read-only
	STATUS current
    DESCRIPTION
        "Set The link9 1R2 Power Status Alarm."
    ::= {link9OBPTrap 28}
	
-- 1.3.6.1.4.1.47477.10.21.9.3.50.29
	link9_powerAlarm2R2 	OBJECT-TYPE    
    SYNTAX DisplayString
	MAX-ACCESS read-only
	STATUS current
    DESCRIPTION
        "Set The link9 2R2 Power Status Alarm."
    ::= {link9OBPTrap 29}
	
-- 1.3.6.1.4.1.47477.10.21.9.3.50.30
	link9_powerAlarm1R3 	OBJECT-TYPE    
    SYNTAX DisplayString
	MAX-ACCESS read-only
	STATUS current
    DESCRIPTION
        "Set The link9 1R3 Power Status Alarm."
    ::= {link9OBPTrap 30}
	
-- 1.3.6.1.4.1.47477.10.21.9.3.50.31
	link9_powerAlarm2R3 	OBJECT-TYPE    
    SYNTAX DisplayString
	MAX-ACCESS read-only
	STATUS current
    DESCRIPTION
        "Set The link9 2R1 Power Status Alarm."
    ::= {link9OBPTrap 31}
	
-- 1.3.6.1.4.1.47477.10.21.9.3.50.32
	link9_powerAlarm1R4 	OBJECT-TYPE    
    SYNTAX DisplayString
	MAX-ACCESS read-only
	STATUS current
    DESCRIPTION
        "Set The link9 1R4 Power Status Alarm."
    ::= {link9OBPTrap 32}
	
-- 1.3.6.1.4.1.47477.10.21.9.3.50.33
	link9_powerAlarm2R4 	OBJECT-TYPE    
    SYNTAX DisplayString
	MAX-ACCESS read-only
	STATUS current
    DESCRIPTION
        "Set The link9 2R4 Power Status Alarm."
    ::= {link9OBPTrap 33}
	
--  1.3.6.1.4.1.47477.10.21.10.3.1
		-- 1.3.6.1.4.1.47477.10.21.10.3.1
		link10_State OBJECT-TYPE
			SYNTAX INTEGER
				{
				off(0),
				on(1)
				}
			MAX-ACCESS read-only
			STATUS current
			DESCRIPTION
				"get the information about whether link10 is working."
			::= { link10OBP 1 }

		
--  1.3.6.1.4.1.47477.10.21.10.3.2
		-- 1.3.6.1.4.1.47477.10.21.10.3.2
		link10_DeviceType OBJECT-TYPE
			SYNTAX DisplayString
			MAX-ACCESS read-only
			STATUS current
			DESCRIPTION
				"get the type of card in link10."
			::= { link10OBP 2 }

			
--  1.3.6.1.4.1.47477.10.21.10.3.3
		-- 1.3.6.1.4.1.47477.10.21.10.3.3
		link10_WorkMode OBJECT-TYPE
			SYNTAX INTEGER
				{
				manualMode(0),
				autoMode(1)
				}
			MAX-ACCESS read-write
			STATUS current
			DESCRIPTION
				"get or set link10's work mode."
			::= { link10OBP 3 }

		
--  1.3.6.1.4.1.47477.10.21.10.3.4
		-- 1.3.6.1.4.1.47477.10.21.10.3.4
		link10_Channel OBJECT-TYPE
			SYNTAX INTEGER
				{
				bypass(0),
				primary(1)
				}
			MAX-ACCESS read-write
			STATUS current
			DESCRIPTION
				"get or set the channel in which link10 works."
			::= { link10OBP 4 }


--  1.3.6.1.4.1.47477.10.21.10.3.5
		-- 1.3.6.1.4.1.47477.10.21.10.3.5
		link10_R1Power OBJECT-TYPE
			SYNTAX DisplayString
			MAX-ACCESS read-only
			STATUS current
			DESCRIPTION
				"get the power of R1 in link10."
			::= { link10OBP 5 }

		
--  1.3.6.1.4.1.47477.10.21.10.3.6
		-- 1.3.6.1.4.1.47477.10.21.10.3.6
		link10_R2Power OBJECT-TYPE
			SYNTAX DisplayString
			MAX-ACCESS read-only
			STATUS current
			DESCRIPTION
				"get the power of R2 in link10."
			::= { link10OBP 6 }
			
--  1.3.6.1.4.1.47477.10.21.10.3.35
		-- 1.3.6.1.4.1.47477.10.21.10.3.35
		link10_R3Power OBJECT-TYPE
			SYNTAX DisplayString
			MAX-ACCESS read-only
			STATUS current
			DESCRIPTION
				"get the power of R3 in link10."
			::= { link10OBP 35 }
			
--  1.3.6.1.4.1.47477.10.21.10.3.36
		-- 1.3.6.1.4.1.47477.10.21.10.3.36
		link10_R4Power OBJECT-TYPE
			SYNTAX DisplayString
			MAX-ACCESS read-only
			STATUS current
			DESCRIPTION
				"get the power of R4 in link10."
			::= { link10OBP 36 }		
		
--  1.3.6.1.4.1.47477.10.21.10.3.7
		-- 1.3.6.1.4.1.47477.10.21.10.3.7
		link10_R1Wave OBJECT-TYPE
			SYNTAX INTEGER
				{
				w1310nm(0),
				w1550nm(1),
				na(2)
				}
			MAX-ACCESS read-write
			STATUS current
			DESCRIPTION
				"get or set the wave length of R1 in link10."
			::= { link10OBP 7 }

		
--  1.3.6.1.4.1.47477.10.21.10.3.8
		-- 1.3.6.1.4.1.47477.10.21.10.3.8
		link10_R2Wave OBJECT-TYPE
			SYNTAX INTEGER
				{
				w1310nm(0),
				w1550nm(1),
				na(2)
				}
			MAX-ACCESS read-write
			STATUS current
			DESCRIPTION
				"get or set the wave length of R2 in link10."
			::= { link10OBP 8 }


--  1.3.6.1.4.1.47477.10.21.10.3.27
		-- 1.3.6.1.4.1.47477.10.21.10.3.27
		link10_R3Wave OBJECT-TYPE
			SYNTAX INTEGER
				{
				w1310nm(0),
				w1550nm(1),
				na(2)
				}
			MAX-ACCESS read-write
			STATUS current
			DESCRIPTION
				"get or set the wave length of R3 in link10."
			::= { link10OBP 27 }

		
--  1.3.6.1.4.1.47477.10.21.10.3.28
		-- 1.3.6.1.4.1.47477.10.21.10.3.28
		link10_R4Wave OBJECT-TYPE
			SYNTAX INTEGER
				{
				w1310nm(0),
				w1550nm(1),
				na(2)
				}
			MAX-ACCESS read-write
			STATUS current
			DESCRIPTION
				"get or set the wave length of R4 in link10."
			::= { link10OBP 28 }
			
--  1.3.6.1.4.1.47477.10.21.10.3.9
		-- 1.3.6.1.4.1.47477.10.21.10.3.9
		link10_R1AlarmPower OBJECT-TYPE
			SYNTAX DisplayString
			MAX-ACCESS read-write
			STATUS current
			DESCRIPTION
				"get or set the power alarm threshold of R1 in link10."
			::= { link10OBP 9 }

		
--  1.3.6.1.4.1.47477.10.21.10.3.10
		-- 1.3.6.1.4.1.47477.10.21.10.3.10
		link10_R2AlarmPower OBJECT-TYPE
			SYNTAX DisplayString
			MAX-ACCESS read-write
			STATUS current
			DESCRIPTION
				"get or set the power alarm threshold of R2 in link10."
			::= { link10OBP 10 }


--  1.3.6.1.4.1.47477.10.21.10.3.29
		-- 1.3.6.1.4.1.47477.10.21.10.3.29
		link10_R3AlarmPower OBJECT-TYPE
			SYNTAX DisplayString
			MAX-ACCESS read-write
			STATUS current
			DESCRIPTION
				"get or set the power alarm threshold of R3 in link10."
			::= { link10OBP 29 }

		
--  1.3.6.1.4.1.47477.10.21.10.3.30
		-- 1.3.6.1.4.1.47477.10.21.10.3.30
		link10_R4AlarmPower OBJECT-TYPE
			SYNTAX DisplayString
			MAX-ACCESS read-write
			STATUS current
			DESCRIPTION
				"get or set the power alarm threshold of R4 in link10."
			::= { link10OBP 30 }

-- OBP4
--  1.3.6.1.4.1.47477.10.21.10.3.37
		-- 1.3.6.1.4.1.47477.10.21.10.3.37
		link10_1R1Power OBJECT-TYPE
			SYNTAX DisplayString
			MAX-ACCESS read-only
			STATUS current
			DESCRIPTION
				"get the power of 1R1 in link10."
			::= { link10OBP 37 }
			
--  1.3.6.1.4.1.47477.10.21.10.3.38
		-- 1.3.6.1.4.1.47477.10.21.10.3.38
		link10_1R2Power OBJECT-TYPE
			SYNTAX DisplayString
			MAX-ACCESS read-only
			STATUS current
			DESCRIPTION
				"get the power of 1R2 in link10."
			::= { link10OBP 38 }

--  1.3.6.1.4.1.47477.10.21.10.3.39
		-- 1.3.6.1.4.1.47477.10.21.10.3.39
		link10_1R3Power OBJECT-TYPE
			SYNTAX DisplayString
			MAX-ACCESS read-only
			STATUS current
			DESCRIPTION
				"get the power of 1R3 in link10."
			::= { link10OBP 39 }
			
--  1.3.6.1.4.1.47477.10.21.10.3.40
		-- 1.3.6.1.4.1.47477.10.21.10.3.40
		link10_1R4Power OBJECT-TYPE
			SYNTAX DisplayString
			MAX-ACCESS read-only
			STATUS current
			DESCRIPTION
				"get the power of 1R4 in link10."
			::= { link10OBP 40 }

--  1.3.6.1.4.1.47477.10.21.10.3.41
		-- 1.3.6.1.4.1.47477.10.21.10.3.41
		link10_2R1Power OBJECT-TYPE
			SYNTAX DisplayString
			MAX-ACCESS read-only
			STATUS current
			DESCRIPTION
				"get the power of 2R1 in link10."
			::= { link10OBP 41 }
			
--  1.3.6.1.4.1.47477.10.21.10.3.42
		-- 1.3.6.1.4.1.47477.10.21.10.3.42
		link10_2R2Power OBJECT-TYPE
			SYNTAX DisplayString
			MAX-ACCESS read-only
			STATUS current
			DESCRIPTION
				"get the power of 2R2 in link10."
			::= { link10OBP 42 }

--  1.3.6.1.4.1.47477.10.21.10.3.41
		-- 1.3.6.1.4.1.47477.10.21.10.3.43
		link10_2R3Power OBJECT-TYPE
			SYNTAX DisplayString
			MAX-ACCESS read-only
			STATUS current
			DESCRIPTION
				"get the power of 2R3 in link10."
			::= { link10OBP 43 }
			
--  1.3.6.1.4.1.47477.10.21.10.3.42
		-- 1.3.6.1.4.1.47477.10.21.10.3.44
		link10_2R4Power OBJECT-TYPE
			SYNTAX DisplayString
			MAX-ACCESS read-only
			STATUS current
			DESCRIPTION
				"get the power of 2R4 in link10."
			::= { link10OBP 44 }
			
--  1.3.6.1.4.1.47477.10.21.10.3.49
		-- 1.3.6.1.4.1.47477.10.21.10.3.49
		link10_1R1Wave OBJECT-TYPE
			SYNTAX INTEGER
				{
				w850nm(0),
				na(2)
				}
			MAX-ACCESS read-only
			STATUS current
			DESCRIPTION
				"get the wave length of 1R1 in link10."
			::= { link10OBP 49 }
		
--  1.3.6.1.4.1.47477.10.21.10.3.60
		-- 1.3.6.1.4.1.47477.10.21.10.3.60
		link10_1R2Wave OBJECT-TYPE
			SYNTAX INTEGER
				{
				w850nm(0),
				na(2)
				}
			MAX-ACCESS read-only
			STATUS current
			DESCRIPTION
				"get the wave length of 1R2 in link10."
			::= { link10OBP 60 }

--  1.3.6.1.4.1.47477.10.21.10.3.61
		-- 1.3.6.1.4.1.47477.10.21.10.3.61
		link10_1R3Wave OBJECT-TYPE
			SYNTAX INTEGER
				{
				w850nm(0),
				na(2)
				}
			MAX-ACCESS read-only
			STATUS current
			DESCRIPTION
				"get the wave length of 1R3 in link10."
			::= { link10OBP 61 }

		
--  1.3.6.1.4.1.47477.10.21.10.3.62
		-- 1.3.6.1.4.1.47477.10.21.10.3.62
		link10_1R4Wave OBJECT-TYPE
			SYNTAX INTEGER
				{
				w850nm(0),
				na(2)
				}
			MAX-ACCESS read-only
			STATUS current
			DESCRIPTION
				"get the wave length of 1R4 in link10."
			::= { link10OBP 62 }
	
--  1.3.6.1.4.1.47477.10.21.10.3.63
		-- 1.3.6.1.4.1.47477.10.21.10.3.63
		link10_2R1Wave OBJECT-TYPE
			SYNTAX INTEGER
				{
				w850nm(0),
				na(2)
				}
			MAX-ACCESS read-only
			STATUS current
			DESCRIPTION
				"get the wave length of 2R1 in link10."
			::= { link10OBP 63 }

		
--  1.3.6.1.4.1.47477.10.21.10.3.64
		-- 1.3.6.1.4.1.47477.10.21.10.3.64
		link10_2R2Wave OBJECT-TYPE
			SYNTAX INTEGER
				{
				w850nm(0),
				na(2)
				}
			MAX-ACCESS read-only
			STATUS current
			DESCRIPTION
				"get the wave length of 2R2 in link10."
			::= { link10OBP 64 }	
	
--  1.3.6.1.4.1.47477.10.21.10.3.65
		-- 1.3.6.1.4.1.47477.10.21.10.3.65
		link10_2R3Wave OBJECT-TYPE
			SYNTAX INTEGER
				{
				w850nm(0),
				na(2)
				}
			MAX-ACCESS read-only
			STATUS current
			DESCRIPTION
				"get the wave length of 2R3 in link10."
			::= { link10OBP 65 }

		
--  1.3.6.1.4.1.47477.10.21.10.3.66
		-- 1.3.6.1.4.1.47477.10.21.10.3.66
		link10_2R4Wave OBJECT-TYPE
			SYNTAX INTEGER
				{
				w850nm(0),
				na(2)
				}
			MAX-ACCESS read-only
			STATUS current
			DESCRIPTION
				"get the wave length of 2R4 in link10."
			::= { link10OBP 66 }	
			
--  1.3.6.1.4.1.47477.10.21.10.3.31
		-- 1.3.6.1.4.1.47477.10.21.10.3.31
		link10_1R1AlarmPower OBJECT-TYPE
			SYNTAX DisplayString
			MAX-ACCESS read-write
			STATUS current
			DESCRIPTION
				"get or set the power alarm threshold of 1R1 in link10."
			::= { link10OBP 31 }
			
--  1.3.6.1.4.1.47477.10.21.10.3.32
		-- 1.3.6.1.4.1.47477.10.21.10.3.32
		link10_1R2AlarmPower OBJECT-TYPE
			SYNTAX DisplayString
			MAX-ACCESS read-write
			STATUS current
			DESCRIPTION
				"get or set the power alarm threshold of 1R2 in link10."
			::= { link10OBP 32 }

--  1.3.6.1.4.1.47477.10.21.10.3.33
		-- 1.3.6.1.4.1.47477.10.21.10.3.33
		link10_1R3AlarmPower OBJECT-TYPE
			SYNTAX DisplayString
			MAX-ACCESS read-write
			STATUS current
			DESCRIPTION
				"get or set the power alarm threshold of 1R3 in link10."
			::= { link10OBP 33 }
			
--  1.3.6.1.4.1.47477.10.21.10.3.34
		-- 1.3.6.1.4.1.47477.10.21.10.3.34
		link10_1R4AlarmPower OBJECT-TYPE
			SYNTAX DisplayString
			MAX-ACCESS read-write
			STATUS current
			DESCRIPTION
				"get or set the power alarm threshold of 1R4 in link10."
			::= { link10OBP 34 }

--  1.3.6.1.4.1.47477.10.21.10.3.45
		-- 1.3.6.1.4.1.47477.10.21.10.3.45
		link10_2R1AlarmPower OBJECT-TYPE
			SYNTAX DisplayString
			MAX-ACCESS read-write
			STATUS current
			DESCRIPTION
				"get or set the power alarm threshold of 2R1 in link10."
			::= { link10OBP 45 }
			
--  1.3.6.1.4.1.47477.10.21.10.3.46
		-- 1.3.6.1.4.1.47477.10.21.10.3.46
		link10_2R2AlarmPower OBJECT-TYPE
			SYNTAX DisplayString
			MAX-ACCESS read-write
			STATUS current
			DESCRIPTION
				"get or set the power alarm threshold of 2R2 in link10."
			::= { link10OBP 46 }

--  1.3.6.1.4.1.47477.10.21.10.3.47
		-- 1.3.6.1.4.1.47477.10.21.10.3.47
		link10_2R3AlarmPower OBJECT-TYPE
			SYNTAX DisplayString
			MAX-ACCESS read-write
			STATUS current
			DESCRIPTION
				"get or set the power alarm threshold of 2R3 in link10."
			::= { link10OBP 47 }
			
--  1.3.6.1.4.1.47477.10.21.10.3.48
		-- 1.3.6.1.4.1.47477.10.21.10.3.48
		link10_2R4AlarmPower OBJECT-TYPE
			SYNTAX DisplayString
			MAX-ACCESS read-write
			STATUS current
			DESCRIPTION
				"get or set the power alarm threshold of 2R4 in link10."
			::= { link10OBP 48 }
			
--  1.3.6.1.4.1.47477.10.21.10.3.11
		-- 1.3.6.1.4.1.47477.10.21.10.3.11
		link10_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link10OBP 11 }
			
--  1.3.6.1.4.1.47477.10.21.10.3.67
		-- 1.3.6.1.4.1.47477.10.21.10.3.67
		link10_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link10OBP 67 }
			
--  1.3.6.1.4.1.47477.10.21.10.3.68
		-- 1.3.6.1.4.1.47477.10.21.10.3.68
		link10_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link10OBP 68 }
			
--  1.3.6.1.4.1.47477.10.21.10.3.12
		-- 1.3.6.1.4.1.47477.10.21.10.3.12
		link10_ReturnDelay OBJECT-TYPE
			--SYNTAX Integer32
			SYNTAX Integer32
			MAX-ACCESS read-write
			STATUS current
			DESCRIPTION
				"get or set how long link10 takes to return to automatic mode."
			::= { link10OBP 12 }
			
--  1.3.6.1.4.1.47477.10.21.10.3.13
		-- 1.3.6.1.4.1.47477.10.21.10.3.13
		link10_BackMode OBJECT-TYPE
			SYNTAX INTEGER
				{
				autoNoBack(0),
				autoBack(1)
				}
			MAX-ACCESS read-write
			STATUS current
			DESCRIPTION
				"get or set the back mode of link10."
			::= { link10OBP 13 }

		
--  1.3.6.1.4.1.47477.10.21.10.3.14
		-- 1.3.6.1.4.1.47477.10.21.10.3.14
		link10_BackDelay OBJECT-TYPE
			SYNTAX Integer32
			MAX-ACCESS read-write
			STATUS current
			DESCRIPTION
				"get or set the back delay."
			::= { link10OBP 14 }

--  1.3.6.1.4.1.47477.10.21.10.3.15
		-- 1.3.6.1.4.1.47477.10.21.10.3.15
		link10_ActiveHeartSwitch OBJECT-TYPE
			SYNTAX INTEGER
				{
				off(0),
				on(1)
				}
			MAX-ACCESS read-write
			STATUS current
			DESCRIPTION
				"get or set the switch status of active heartbeat."
			::= { link10OBP 15 }

		
--  1.3.6.1.4.1.47477.10.21.10.3.16
		-- 1.3.6.1.4.1.47477.10.21.10.3.16
		link10_ActiveSendInterval OBJECT-TYPE
			SYNTAX Integer32
			MAX-ACCESS read-write
			STATUS current
			DESCRIPTION
				"get or set the send interval of active heartbeat."
			::= { link10OBP 16 }		

--  1.3.6.1.4.1.47477.10.21.10.3.17
		-- 1.3.6.1.4.1.47477.10.21.10.3.17
		link10_ActiveTimeOut OBJECT-TYPE
			SYNTAX Integer32
			MAX-ACCESS read-write
			STATUS current
			DESCRIPTION
				"get or set how long the active heartbeat send timeout."
			::= { link10OBP 17 }

--  1.3.6.1.4.1.47477.10.21.10.3.18
		-- 1.3.6.1.4.1.47477.10.21.10.3.18
		link10_ActiveLossBypass OBJECT-TYPE
			SYNTAX Integer32
			MAX-ACCESS read-write
			STATUS current
			DESCRIPTION
				"get or set the bypass for active heartbeat packet loss."
			::= { link10OBP 18 }

--  1.3.6.1.4.1.47477.10.21.10.3.19
		-- 1.3.6.1.4.1.47477.10.21.10.3.19
		link10_PingIpAddress OBJECT-TYPE
			SYNTAX IpAddress
			MAX-ACCESS read-write
			STATUS current
			DESCRIPTION
				"get or set the ping ip address of link10."
			::= { link10OBP 19 }

--  1.3.6.1.4.1.47477.10.21.10.3.20
		-- 1.3.6.1.4.1.47477.10.21.10.3.20
		link10_PassiveHeartSwitch OBJECT-TYPE
			SYNTAX INTEGER
				{
				off(0),
				on(1)
				}
			MAX-ACCESS read-write
			STATUS current
			DESCRIPTION
				"get or set the switch status of passive heartbeat."
			::= { link10OBP 20 }
	

--  1.3.6.1.4.1.47477.10.21.10.3.21
		-- 1.3.6.1.4.1.47477.10.21.10.3.21
		link10_PassiveTimeOut OBJECT-TYPE
			SYNTAX Integer32
			MAX-ACCESS read-write
			STATUS current
			DESCRIPTION
				"get or set how long the passive heartbeat send timeout."
			::= { link10OBP 21 }

--  1.3.6.1.4.1.47477.10.21.10.3.22
		-- 1.3.6.1.4.1.47477.10.21.10.3.22
		link10_PassiveLossBypass OBJECT-TYPE
			SYNTAX Integer32
			MAX-ACCESS read-write
			STATUS current
			DESCRIPTION
				"get or set the bypass for passive heartbeat packet loss."
			::= { link10OBP 22 }

--  1.3.6.1.4.1.47477.10.21.10.3.23
		-- 1.3.6.1.4.1.47477.10.21.10.3.23
		link10_SwitchProtect OBJECT-TYPE
			SYNTAX INTEGER
				{
				off(0),
				on(1)
				}
			MAX-ACCESS read-write
			STATUS current
			DESCRIPTION
				"get or set the switch protection status of link10."
			::= { link10OBP 23 }
			
--  1.3.6.1.4.1.47477.10.21.10.3.24
		-- 1.3.6.1.4.1.47477.10.21.10.3.24
		link10_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link10OBP 24 }		

--  1.3.6.1.4.1.47477.10.21.10.3.25
		-- 1.3.6.1.4.1.47477.10.21.10.3.25
		link10_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link10OBP 25 }	

--  1.3.6.1.4.1.47477.10.21.10.3.26
		-- 1.3.6.1.4.1.47477.10.21.10.3.26
		link10_PowerAlarmStatus OBJECT-TYPE
			SYNTAX INTEGER
				{
				off(0),
				alarm(1),
				normal(2),
				na(3)
				}
			MAX-ACCESS read-only
			STATUS current
			DESCRIPTION
				"get whether a power alarm is generated."
			::= { link10OBP 26 }	


-- 1.3.6.1.4.1.47477.10.21.10.3.50.1
	link10_WorkModeChange 	OBJECT-TYPE    
    SYNTAX INTEGER	{
				manualMode(0),
				autoMode(1)
		}
	MAX-ACCESS read-only
	STATUS current
    DESCRIPTION
        "The Link mode Changed."
    ::= {link10OBPTrap 1}

-- 1.3.6.1.4.1.47477.10.21.10.3.50.2
	link10_StateChange 	OBJECT-TYPE    
    SYNTAX INTEGER	{
				bypass(0),
				primary(1)
		}
	MAX-ACCESS read-only
	STATUS current
    DESCRIPTION
        "The Link State(Channel) Changed."
    ::= {link10OBPTrap 2}

-- 1.3.6.1.4.1.47477.10.21.10.3.50.3
	link10_R1WaveSet 	OBJECT-TYPE    
    SYNTAX INTEGER	{
				w1310nm(0),
				w1550nm(1)
		}
	MAX-ACCESS read-only
	STATUS current
    DESCRIPTION
        "Set The link10 R1 Wave."
    ::= {link10OBPTrap 3}

-- 1.3.6.1.4.1.47477.10.21.10.3.50.4
	link10_R2WaveSet 	OBJECT-TYPE    
    SYNTAX INTEGER	{
				w1310nm(0),
				w1550nm(1)
		}
	MAX-ACCESS read-only
	STATUS current
    DESCRIPTION
        "Set The link10 R2 Wave."
    ::= {link10OBPTrap 4}			

-- 1.3.6.1.4.1.47477.10.21.10.3.50.5
	link10_R3WaveSet 	OBJECT-TYPE    
    SYNTAX INTEGER	{
				w1310nm(0),
				w1550nm(1)
		}
	MAX-ACCESS read-only
	STATUS current
    DESCRIPTION
        "Set The link10 R3 Wave."
    ::= {link10OBPTrap 5}

-- 1.3.6.1.4.1.47477.10.21.10.3.50.6
	link10_R4WaveSet 	OBJECT-TYPE    
    SYNTAX INTEGER	{
				w1310nm(0),
				w1550nm(1)
		}
	MAX-ACCESS read-only
	STATUS current
    DESCRIPTION
        "Set The link10 R4 Wave."
    ::= {link10OBPTrap 6}	
	
-- 1.3.6.1.4.1.47477.10.21.10.3.50.7
	link10_R1AlarmSet 	OBJECT-TYPE    
    SYNTAX DisplayString
	MAX-ACCESS read-only
	STATUS current
    DESCRIPTION
        "Set The link10 R1 Alarm Threshold."
    ::= {link10OBPTrap 7}

-- 1.3.6.1.4.1.47477.10.21.10.3.50.8
	link10_R2AlarmSet 	OBJECT-TYPE    
    SYNTAX DisplayString
	MAX-ACCESS read-only
	STATUS current
    DESCRIPTION
        "Set The link10 R2 Alarm Threshold."
    ::= {link10OBPTrap 8}
	
-- 1.3.6.1.4.1.47477.10.21.10.3.50.9
	link10_R3AlarmSet 	OBJECT-TYPE    
    SYNTAX DisplayString
	MAX-ACCESS read-only
	STATUS current
    DESCRIPTION
        "Set The link10 R3 Alarm Threshold."
    ::= {link10OBPTrap 9}

-- 1.3.6.1.4.1.47477.10.21.10.3.50.10
	link10_R4AlarmSet 	OBJECT-TYPE    
    SYNTAX DisplayString
	MAX-ACCESS read-only
	STATUS current
    DESCRIPTION
        "Set The link10 R4 Alarm Threshold."
    ::= {link10OBPTrap 10}	
	
	
-- 1.3.6.1.4.1.47477.10.21.10.3.50.11
	link10_1R1AlarmSet 	OBJECT-TYPE    
    SYNTAX DisplayString
	MAX-ACCESS read-only
	STATUS current
    DESCRIPTION
        "Set The link10 1R1 Alarm Threshold."
    ::= {link10OBPTrap 11}

-- 1.3.6.1.4.1.47477.10.21.10.3.50.12
	link10_2R1AlarmSet 	OBJECT-TYPE    
    SYNTAX DisplayString
	MAX-ACCESS read-only
	STATUS current
    DESCRIPTION
        "Set The link10 2R1 Alarm Threshold."
    ::= {link10OBPTrap 12}
	
-- 1.3.6.1.4.1.47477.10.21.10.3.50.13
	link10_1R2AlarmSet 	OBJECT-TYPE    
    SYNTAX DisplayString
	MAX-ACCESS read-only
	STATUS current
    DESCRIPTION
        "Set The link10 1R2 Alarm Threshold."
    ::= {link10OBPTrap 13}

-- 1.3.6.1.4.1.47477.10.21.10.3.50.14
	link10_2R2AlarmSet 	OBJECT-TYPE    
    SYNTAX DisplayString
	MAX-ACCESS read-only
	STATUS current
    DESCRIPTION
        "Set The link10 2R2 Alarm Threshold."
    ::= {link10OBPTrap 14}
	
-- 1.3.6.1.4.1.47477.10.21.10.3.50.15
	link10_1R3AlarmSet 	OBJECT-TYPE    
    SYNTAX DisplayString
	MAX-ACCESS read-only
	STATUS current
    DESCRIPTION
        "Set The link10 1R3 Alarm Threshold."
    ::= {link10OBPTrap 15}

-- 1.3.6.1.4.1.47477.10.21.10.3.50.16
	link10_2R3AlarmSet 	OBJECT-TYPE    
    SYNTAX DisplayString
	MAX-ACCESS read-only
	STATUS current
    DESCRIPTION
        "Set The link10 2R3 Alarm Threshold."
    ::= {link10OBPTrap 16}
	
-- 1.3.6.1.4.1.47477.10.21.10.3.50.17
	link10_1R4AlarmSet 	OBJECT-TYPE    
    SYNTAX DisplayString
	MAX-ACCESS read-only
	STATUS current
    DESCRIPTION
        "Set The link10 1R4 Alarm Threshold."
    ::= {link10OBPTrap 17}

-- 1.3.6.1.4.1.47477.10.21.10.3.50.18
	link10_2R4AlarmSet 	OBJECT-TYPE    
    SYNTAX DisplayString
	MAX-ACCESS read-only
	STATUS current
    DESCRIPTION
        "Set The link10 2R4 Alarm Threshold."
    ::= {link10OBPTrap 18}
	
-- 1.3.6.1.4.1.47477.10.21.10.3.50.19
	link10_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link10 PowerAlarmBypass2 Changed."
    ::= {link10OBPTrap 19}
	
-- 1.3.6.1.4.1.47477.10.21.10.3.50.20
	link10_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link10 PowerAlarmBypass4 Changed."
    ::= {link10OBPTrap 20}	
	
-- 1.3.6.1.4.1.47477.10.21.10.3.50.21
	link10_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link10 PowerAlarmBypass8 Changed."
    ::= {link10OBPTrap 21}
	
-- 1.3.6.1.4.1.47477.10.21.10.3.50.22
	link10_powerAlarmR1 	OBJECT-TYPE    
    SYNTAX DisplayString
	MAX-ACCESS read-only
	STATUS current
    DESCRIPTION
        "Set The link10 R1 Power Status Alarm."
    ::= {link10OBPTrap 22}
	
-- 1.3.6.1.4.1.47477.10.21.10.3.50.23
	link10_powerAlarmR2 	OBJECT-TYPE    
    SYNTAX DisplayString
	MAX-ACCESS read-only
	STATUS current
    DESCRIPTION
        "Set The link10 R2 Power Status Alarm."
    ::= {link10OBPTrap 23}
	
-- 1.3.6.1.4.1.47477.10.21.10.3.50.24
	link10_powerAlarmR3 	OBJECT-TYPE    
    SYNTAX DisplayString
	MAX-ACCESS read-only
	STATUS current
    DESCRIPTION
        "Set The link10 R3 Power Status Alarm."
    ::= {link10OBPTrap 24}
	
-- 1.3.6.1.4.1.47477.10.21.10.3.50.25
	link10_powerAlarmR4 	OBJECT-TYPE    
    SYNTAX DisplayString
	MAX-ACCESS read-only
	STATUS current
    DESCRIPTION
        "Set The link10 R4 Power Status Alarm."
    ::= {link10OBPTrap 25}
	
	
-- 1.3.6.1.4.1.47477.10.21.10.3.50.26
	link10_powerAlarm1R1 	OBJECT-TYPE    
    SYNTAX DisplayString
	MAX-ACCESS read-only
	STATUS current
    DESCRIPTION
        "Set The link10 1R1 Power Status Alarm."
    ::= {link10OBPTrap 26}
	
-- 1.3.6.1.4.1.47477.10.21.10.3.50.27
	link10_powerAlarm2R1 	OBJECT-TYPE    
    SYNTAX DisplayString
	MAX-ACCESS read-only
	STATUS current
    DESCRIPTION
        "Set The link10 2R1 Power Status Alarm."
    ::= {link10OBPTrap 27}
	
-- 1.3.6.1.4.1.47477.10.21.10.3.50.28
	link10_powerAlarm1R2 	OBJECT-TYPE    
    SYNTAX DisplayString
	MAX-ACCESS read-only
	STATUS current
    DESCRIPTION
        "Set The link10 1R2 Power Status Alarm."
    ::= {link10OBPTrap 28}
	
-- 1.3.6.1.4.1.47477.10.21.10.3.50.29
	link10_powerAlarm2R2 	OBJECT-TYPE    
    SYNTAX DisplayString
	MAX-ACCESS read-only
	STATUS current
    DESCRIPTION
        "Set The link10 2R2 Power Status Alarm."
    ::= {link10OBPTrap 29}
	
-- 1.3.6.1.4.1.47477.10.21.10.3.50.30
	link10_powerAlarm1R3 	OBJECT-TYPE    
    SYNTAX DisplayString
	MAX-ACCESS read-only
	STATUS current
    DESCRIPTION
        "Set The link10 1R3 Power Status Alarm."
    ::= {link10OBPTrap 30}
	
-- 1.3.6.1.4.1.47477.10.21.10.3.50.31
	link10_powerAlarm2R3 	OBJECT-TYPE    
    SYNTAX DisplayString
	MAX-ACCESS read-only
	STATUS current
    DESCRIPTION
        "Set The link10 2R1 Power Status Alarm."
    ::= {link10OBPTrap 31}
	
-- 1.3.6.1.4.1.47477.10.21.10.3.50.32
	link10_powerAlarm1R4 	OBJECT-TYPE    
    SYNTAX DisplayString
	MAX-ACCESS read-only
	STATUS current
    DESCRIPTION
        "Set The link10 1R4 Power Status Alarm."
    ::= {link10OBPTrap 32}
	
-- 1.3.6.1.4.1.47477.10.21.10.3.50.33
	link10_powerAlarm2R4 	OBJECT-TYPE    
    SYNTAX DisplayString
	MAX-ACCESS read-only
	STATUS current
    DESCRIPTION
        "Set The link10 2R4 Power Status Alarm."
    ::= {link10OBPTrap 33}
	
--  1.3.6.1.4.1.47477.10.21.11.3.1
		-- 1.3.6.1.4.1.47477.10.21.11.3.1
		link11_State OBJECT-TYPE
			SYNTAX INTEGER
				{
				off(0),
				on(1)
				}
			MAX-ACCESS read-only
			STATUS current
			DESCRIPTION
				"get the information about whether link11 is working."
			::= { link11OBP 1 }

		
--  1.3.6.1.4.1.47477.10.21.11.3.2
		-- 1.3.6.1.4.1.47477.10.21.11.3.2
		link11_DeviceType OBJECT-TYPE
			SYNTAX DisplayString
			MAX-ACCESS read-only
			STATUS current
			DESCRIPTION
				"get the type of card in link11."
			::= { link11OBP 2 }

			
--  1.3.6.1.4.1.47477.10.21.11.3.3
		-- 1.3.6.1.4.1.47477.10.21.11.3.3
		link11_WorkMode OBJECT-TYPE
			SYNTAX INTEGER
				{
				manualMode(0),
				autoMode(1)
				}
			MAX-ACCESS read-write
			STATUS current
			DESCRIPTION
				"get or set link11's work mode."
			::= { link11OBP 3 }

		
--  1.3.6.1.4.1.47477.10.21.11.3.4
		-- 1.3.6.1.4.1.47477.10.21.11.3.4
		link11_Channel OBJECT-TYPE
			SYNTAX INTEGER
				{
				bypass(0),
				primary(1)
				}
			MAX-ACCESS read-write
			STATUS current
			DESCRIPTION
				"get or set the channel in which link11 works."
			::= { link11OBP 4 }


--  1.3.6.1.4.1.47477.10.21.11.3.5
		-- 1.3.6.1.4.1.47477.10.21.11.3.5
		link11_R1Power OBJECT-TYPE
			SYNTAX DisplayString
			MAX-ACCESS read-only
			STATUS current
			DESCRIPTION
				"get the power of R1 in link11."
			::= { link11OBP 5 }

		
--  1.3.6.1.4.1.47477.10.21.11.3.6
		-- 1.3.6.1.4.1.47477.10.21.11.3.6
		link11_R2Power OBJECT-TYPE
			SYNTAX DisplayString
			MAX-ACCESS read-only
			STATUS current
			DESCRIPTION
				"get the power of R2 in link11."
			::= { link11OBP 6 }
			
--  1.3.6.1.4.1.47477.10.21.11.3.35
		-- 1.3.6.1.4.1.47477.10.21.11.3.35
		link11_R3Power OBJECT-TYPE
			SYNTAX DisplayString
			MAX-ACCESS read-only
			STATUS current
			DESCRIPTION
				"get the power of R3 in link11."
			::= { link11OBP 35 }
			
--  1.3.6.1.4.1.47477.10.21.11.3.36
		-- 1.3.6.1.4.1.47477.10.21.11.3.36
		link11_R4Power OBJECT-TYPE
			SYNTAX DisplayString
			MAX-ACCESS read-only
			STATUS current
			DESCRIPTION
				"get the power of R4 in link11."
			::= { link11OBP 36 }		
		
--  1.3.6.1.4.1.47477.10.21.11.3.7
		-- 1.3.6.1.4.1.47477.10.21.11.3.7
		link11_R1Wave OBJECT-TYPE
			SYNTAX INTEGER
				{
				w1310nm(0),
				w1550nm(1),
				na(2)
				}
			MAX-ACCESS read-write
			STATUS current
			DESCRIPTION
				"get or set the wave length of R1 in link11."
			::= { link11OBP 7 }

		
--  1.3.6.1.4.1.47477.10.21.11.3.8
		-- 1.3.6.1.4.1.47477.10.21.11.3.8
		link11_R2Wave OBJECT-TYPE
			SYNTAX INTEGER
				{
				w1310nm(0),
				w1550nm(1),
				na(2)
				}
			MAX-ACCESS read-write
			STATUS current
			DESCRIPTION
				"get or set the wave length of R2 in link11."
			::= { link11OBP 8 }


--  1.3.6.1.4.1.47477.10.21.11.3.27
		-- 1.3.6.1.4.1.47477.10.21.11.3.27
		link11_R3Wave OBJECT-TYPE
			SYNTAX INTEGER
				{
				w1310nm(0),
				w1550nm(1),
				na(2)
				}
			MAX-ACCESS read-write
			STATUS current
			DESCRIPTION
				"get or set the wave length of R3 in link11."
			::= { link11OBP 27 }

		
--  1.3.6.1.4.1.47477.10.21.11.3.28
		-- 1.3.6.1.4.1.47477.10.21.11.3.28
		link11_R4Wave OBJECT-TYPE
			SYNTAX INTEGER
				{
				w1310nm(0),
				w1550nm(1),
				na(2)
				}
			MAX-ACCESS read-write
			STATUS current
			DESCRIPTION
				"get or set the wave length of R4 in link11."
			::= { link11OBP 28 }
			
--  1.3.6.1.4.1.47477.10.21.11.3.9
		-- 1.3.6.1.4.1.47477.10.21.11.3.9
		link11_R1AlarmPower OBJECT-TYPE
			SYNTAX DisplayString
			MAX-ACCESS read-write
			STATUS current
			DESCRIPTION
				"get or set the power alarm threshold of R1 in link11."
			::= { link11OBP 9 }

		
--  1.3.6.1.4.1.47477.10.21.11.3.10
		-- 1.3.6.1.4.1.47477.10.21.11.3.10
		link11_R2AlarmPower OBJECT-TYPE
			SYNTAX DisplayString
			MAX-ACCESS read-write
			STATUS current
			DESCRIPTION
				"get or set the power alarm threshold of R2 in link11."
			::= { link11OBP 10 }


--  1.3.6.1.4.1.47477.10.21.11.3.29
		-- 1.3.6.1.4.1.47477.10.21.11.3.29
		link11_R3AlarmPower OBJECT-TYPE
			SYNTAX DisplayString
			MAX-ACCESS read-write
			STATUS current
			DESCRIPTION
				"get or set the power alarm threshold of R3 in link11."
			::= { link11OBP 29 }

		
--  1.3.6.1.4.1.47477.10.21.11.3.30
		-- 1.3.6.1.4.1.47477.10.21.11.3.30
		link11_R4AlarmPower OBJECT-TYPE
			SYNTAX DisplayString
			MAX-ACCESS read-write
			STATUS current
			DESCRIPTION
				"get or set the power alarm threshold of R4 in link11."
			::= { link11OBP 30 }

-- OBP4
--  1.3.6.1.4.1.47477.10.21.11.3.37
		-- 1.3.6.1.4.1.47477.10.21.11.3.37
		link11_1R1Power OBJECT-TYPE
			SYNTAX DisplayString
			MAX-ACCESS read-only
			STATUS current
			DESCRIPTION
				"get the power of 1R1 in link11."
			::= { link11OBP 37 }
			
--  1.3.6.1.4.1.47477.10.21.11.3.38
		-- 1.3.6.1.4.1.47477.10.21.11.3.38
		link11_1R2Power OBJECT-TYPE
			SYNTAX DisplayString
			MAX-ACCESS read-only
			STATUS current
			DESCRIPTION
				"get the power of 1R2 in link11."
			::= { link11OBP 38 }

--  1.3.6.1.4.1.47477.10.21.11.3.39
		-- 1.3.6.1.4.1.47477.10.21.11.3.39
		link11_1R3Power OBJECT-TYPE
			SYNTAX DisplayString
			MAX-ACCESS read-only
			STATUS current
			DESCRIPTION
				"get the power of 1R3 in link11."
			::= { link11OBP 39 }
			
--  1.3.6.1.4.1.47477.10.21.11.3.40
		-- 1.3.6.1.4.1.47477.10.21.11.3.40
		link11_1R4Power OBJECT-TYPE
			SYNTAX DisplayString
			MAX-ACCESS read-only
			STATUS current
			DESCRIPTION
				"get the power of 1R4 in link11."
			::= { link11OBP 40 }

--  1.3.6.1.4.1.47477.10.21.11.3.41
		-- 1.3.6.1.4.1.47477.10.21.11.3.41
		link11_2R1Power OBJECT-TYPE
			SYNTAX DisplayString
			MAX-ACCESS read-only
			STATUS current
			DESCRIPTION
				"get the power of 2R1 in link11."
			::= { link11OBP 41 }
			
--  1.3.6.1.4.1.47477.10.21.11.3.42
		-- 1.3.6.1.4.1.47477.10.21.11.3.42
		link11_2R2Power OBJECT-TYPE
			SYNTAX DisplayString
			MAX-ACCESS read-only
			STATUS current
			DESCRIPTION
				"get the power of 2R2 in link11."
			::= { link11OBP 42 }

--  1.3.6.1.4.1.47477.10.21.11.3.41
		-- 1.3.6.1.4.1.47477.10.21.11.3.43
		link11_2R3Power OBJECT-TYPE
			SYNTAX DisplayString
			MAX-ACCESS read-only
			STATUS current
			DESCRIPTION
				"get the power of 2R3 in link11."
			::= { link11OBP 43 }
			
--  1.3.6.1.4.1.47477.10.21.11.3.42
		-- 1.3.6.1.4.1.47477.10.21.11.3.44
		link11_2R4Power OBJECT-TYPE
			SYNTAX DisplayString
			MAX-ACCESS read-only
			STATUS current
			DESCRIPTION
				"get the power of 2R4 in link11."
			::= { link11OBP 44 }
			
--  1.3.6.1.4.1.47477.10.21.11.3.49
		-- 1.3.6.1.4.1.47477.10.21.11.3.49
		link11_1R1Wave OBJECT-TYPE
			SYNTAX INTEGER
				{
				w850nm(0),
				na(2)
				}
			MAX-ACCESS read-only
			STATUS current
			DESCRIPTION
				"get the wave length of 1R1 in link11."
			::= { link11OBP 49 }
		
--  1.3.6.1.4.1.47477.10.21.11.3.60
		-- 1.3.6.1.4.1.47477.10.21.11.3.60
		link11_1R2Wave OBJECT-TYPE
			SYNTAX INTEGER
				{
				w850nm(0),
				na(2)
				}
			MAX-ACCESS read-only
			STATUS current
			DESCRIPTION
				"get the wave length of 1R2 in link11."
			::= { link11OBP 60 }

--  1.3.6.1.4.1.47477.10.21.11.3.61
		-- 1.3.6.1.4.1.47477.10.21.11.3.61
		link11_1R3Wave OBJECT-TYPE
			SYNTAX INTEGER
				{
				w850nm(0),
				na(2)
				}
			MAX-ACCESS read-only
			STATUS current
			DESCRIPTION
				"get the wave length of 1R3 in link11."
			::= { link11OBP 61 }

		
--  1.3.6.1.4.1.47477.10.21.11.3.62
		-- 1.3.6.1.4.1.47477.10.21.11.3.62
		link11_1R4Wave OBJECT-TYPE
			SYNTAX INTEGER
				{
				w850nm(0),
				na(2)
				}
			MAX-ACCESS read-only
			STATUS current
			DESCRIPTION
				"get the wave length of 1R4 in link11."
			::= { link11OBP 62 }
	
--  1.3.6.1.4.1.47477.10.21.11.3.63
		-- 1.3.6.1.4.1.47477.10.21.11.3.63
		link11_2R1Wave OBJECT-TYPE
			SYNTAX INTEGER
				{
				w850nm(0),
				na(2)
				}
			MAX-ACCESS read-only
			STATUS current
			DESCRIPTION
				"get the wave length of 2R1 in link11."
			::= { link11OBP 63 }

		
--  1.3.6.1.4.1.47477.10.21.11.3.64
		-- 1.3.6.1.4.1.47477.10.21.11.3.64
		link11_2R2Wave OBJECT-TYPE
			SYNTAX INTEGER
				{
				w850nm(0),
				na(2)
				}
			MAX-ACCESS read-only
			STATUS current
			DESCRIPTION
				"get the wave length of 2R2 in link11."
			::= { link11OBP 64 }	
	
--  1.3.6.1.4.1.47477.10.21.11.3.65
		-- 1.3.6.1.4.1.47477.10.21.11.3.65
		link11_2R3Wave OBJECT-TYPE
			SYNTAX INTEGER
				{
				w850nm(0),
				na(2)
				}
			MAX-ACCESS read-only
			STATUS current
			DESCRIPTION
				"get the wave length of 2R3 in link11."
			::= { link11OBP 65 }

		
--  1.3.6.1.4.1.47477.10.21.11.3.66
		-- 1.3.6.1.4.1.47477.10.21.11.3.66
		link11_2R4Wave OBJECT-TYPE
			SYNTAX INTEGER
				{
				w850nm(0),
				na(2)
				}
			MAX-ACCESS read-only
			STATUS current
			DESCRIPTION
				"get the wave length of 2R4 in link11."
			::= { link11OBP 66 }	
			
--  1.3.6.1.4.1.47477.10.21.11.3.31
		-- 1.3.6.1.4.1.47477.10.21.11.3.31
		link11_1R1AlarmPower OBJECT-TYPE
			SYNTAX DisplayString
			MAX-ACCESS read-write
			STATUS current
			DESCRIPTION
				"get or set the power alarm threshold of 1R1 in link11."
			::= { link11OBP 31 }
			
--  1.3.6.1.4.1.47477.10.21.11.3.32
		-- 1.3.6.1.4.1.47477.10.21.11.3.32
		link11_1R2AlarmPower OBJECT-TYPE
			SYNTAX DisplayString
			MAX-ACCESS read-write
			STATUS current
			DESCRIPTION
				"get or set the power alarm threshold of 1R2 in link11."
			::= { link11OBP 32 }

--  1.3.6.1.4.1.47477.10.21.11.3.33
		-- 1.3.6.1.4.1.47477.10.21.11.3.33
		link11_1R3AlarmPower OBJECT-TYPE
			SYNTAX DisplayString
			MAX-ACCESS read-write
			STATUS current
			DESCRIPTION
				"get or set the power alarm threshold of 1R3 in link11."
			::= { link11OBP 33 }
			
--  1.3.6.1.4.1.47477.10.21.11.3.34
		-- 1.3.6.1.4.1.47477.10.21.11.3.34
		link11_1R4AlarmPower OBJECT-TYPE
			SYNTAX DisplayString
			MAX-ACCESS read-write
			STATUS current
			DESCRIPTION
				"get or set the power alarm threshold of 1R4 in link11."
			::= { link11OBP 34 }

--  1.3.6.1.4.1.47477.10.21.11.3.45
		-- 1.3.6.1.4.1.47477.10.21.11.3.45
		link11_2R1AlarmPower OBJECT-TYPE
			SYNTAX DisplayString
			MAX-ACCESS read-write
			STATUS current
			DESCRIPTION
				"get or set the power alarm threshold of 2R1 in link11."
			::= { link11OBP 45 }
			
--  1.3.6.1.4.1.47477.10.21.11.3.46
		-- 1.3.6.1.4.1.47477.10.21.11.3.46
		link11_2R2AlarmPower OBJECT-TYPE
			SYNTAX DisplayString
			MAX-ACCESS read-write
			STATUS current
			DESCRIPTION
				"get or set the power alarm threshold of 2R2 in link11."
			::= { link11OBP 46 }

--  1.3.6.1.4.1.47477.10.21.11.3.47
		-- 1.3.6.1.4.1.47477.10.21.11.3.47
		link11_2R3AlarmPower OBJECT-TYPE
			SYNTAX DisplayString
			MAX-ACCESS read-write
			STATUS current
			DESCRIPTION
				"get or set the power alarm threshold of 2R3 in link11."
			::= { link11OBP 47 }
			
--  1.3.6.1.4.1.47477.10.21.11.3.48
		-- 1.3.6.1.4.1.47477.10.21.11.3.48
		link11_2R4AlarmPower OBJECT-TYPE
			SYNTAX DisplayString
			MAX-ACCESS read-write
			STATUS current
			DESCRIPTION
				"get or set the power alarm threshold of 2R4 in link11."
			::= { link11OBP 48 }
			
--  1.3.6.1.4.1.47477.10.21.11.3.11
		-- 1.3.6.1.4.1.47477.10.21.11.3.11
		link11_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link11OBP 11 }
			
--  1.3.6.1.4.1.47477.10.21.11.3.67
		-- 1.3.6.1.4.1.47477.10.21.11.3.67
		link11_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link11OBP 67 }
			
--  1.3.6.1.4.1.47477.10.21.11.3.68
		-- 1.3.6.1.4.1.47477.10.21.11.3.68
		link11_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link11OBP 68 }
			
--  1.3.6.1.4.1.47477.10.21.11.3.12
		-- 1.3.6.1.4.1.47477.10.21.11.3.12
		link11_ReturnDelay OBJECT-TYPE
			--SYNTAX Integer32
			SYNTAX Integer32
			MAX-ACCESS read-write
			STATUS current
			DESCRIPTION
				"get or set how long link11 takes to return to automatic mode."
			::= { link11OBP 12 }
			
--  1.3.6.1.4.1.47477.10.21.11.3.13
		-- 1.3.6.1.4.1.47477.10.21.11.3.13
		link11_BackMode OBJECT-TYPE
			SYNTAX INTEGER
				{
				autoNoBack(0),
				autoBack(1)
				}
			MAX-ACCESS read-write
			STATUS current
			DESCRIPTION
				"get or set the back mode of link11."
			::= { link11OBP 13 }

		
--  1.3.6.1.4.1.47477.10.21.11.3.14
		-- 1.3.6.1.4.1.47477.10.21.11.3.14
		link11_BackDelay OBJECT-TYPE
			SYNTAX Integer32
			MAX-ACCESS read-write
			STATUS current
			DESCRIPTION
				"get or set the back delay."
			::= { link11OBP 14 }

--  1.3.6.1.4.1.47477.10.21.11.3.15
		-- 1.3.6.1.4.1.47477.10.21.11.3.15
		link11_ActiveHeartSwitch OBJECT-TYPE
			SYNTAX INTEGER
				{
				off(0),
				on(1)
				}
			MAX-ACCESS read-write
			STATUS current
			DESCRIPTION
				"get or set the switch status of active heartbeat."
			::= { link11OBP 15 }

		
--  1.3.6.1.4.1.47477.10.21.11.3.16
		-- 1.3.6.1.4.1.47477.10.21.11.3.16
		link11_ActiveSendInterval OBJECT-TYPE
			SYNTAX Integer32
			MAX-ACCESS read-write
			STATUS current
			DESCRIPTION
				"get or set the send interval of active heartbeat."
			::= { link11OBP 16 }		

--  1.3.6.1.4.1.47477.10.21.11.3.17
		-- 1.3.6.1.4.1.47477.10.21.11.3.17
		link11_ActiveTimeOut OBJECT-TYPE
			SYNTAX Integer32
			MAX-ACCESS read-write
			STATUS current
			DESCRIPTION
				"get or set how long the active heartbeat send timeout."
			::= { link11OBP 17 }

--  1.3.6.1.4.1.47477.10.21.11.3.18
		-- 1.3.6.1.4.1.47477.10.21.11.3.18
		link11_ActiveLossBypass OBJECT-TYPE
			SYNTAX Integer32
			MAX-ACCESS read-write
			STATUS current
			DESCRIPTION
				"get or set the bypass for active heartbeat packet loss."
			::= { link11OBP 18 }

--  1.3.6.1.4.1.47477.10.21.11.3.19
		-- 1.3.6.1.4.1.47477.10.21.11.3.19
		link11_PingIpAddress OBJECT-TYPE
			SYNTAX IpAddress
			MAX-ACCESS read-write
			STATUS current
			DESCRIPTION
				"get or set the ping ip address of link11."
			::= { link11OBP 19 }

--  1.3.6.1.4.1.47477.10.21.11.3.20
		-- 1.3.6.1.4.1.47477.10.21.11.3.20
		link11_PassiveHeartSwitch OBJECT-TYPE
			SYNTAX INTEGER
				{
				off(0),
				on(1)
				}
			MAX-ACCESS read-write
			STATUS current
			DESCRIPTION
				"get or set the switch status of passive heartbeat."
			::= { link11OBP 20 }
	

--  1.3.6.1.4.1.47477.10.21.11.3.21
		-- 1.3.6.1.4.1.47477.10.21.11.3.21
		link11_PassiveTimeOut OBJECT-TYPE
			SYNTAX Integer32
			MAX-ACCESS read-write
			STATUS current
			DESCRIPTION
				"get or set how long the passive heartbeat send timeout."
			::= { link11OBP 21 }

--  1.3.6.1.4.1.47477.10.21.11.3.22
		-- 1.3.6.1.4.1.47477.10.21.11.3.22
		link11_PassiveLossBypass OBJECT-TYPE
			SYNTAX Integer32
			MAX-ACCESS read-write
			STATUS current
			DESCRIPTION
				"get or set the bypass for passive heartbeat packet loss."
			::= { link11OBP 22 }

--  1.3.6.1.4.1.47477.10.21.11.3.23
		-- 1.3.6.1.4.1.47477.10.21.11.3.23
		link11_SwitchProtect OBJECT-TYPE
			SYNTAX INTEGER
				{
				off(0),
				on(1)
				}
			MAX-ACCESS read-write
			STATUS current
			DESCRIPTION
				"get or set the switch protection status of link11."
			::= { link11OBP 23 }
			
--  1.3.6.1.4.1.47477.10.21.11.3.24
		-- 1.3.6.1.4.1.47477.10.21.11.3.24
		link11_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link11OBP 24 }		

--  1.3.6.1.4.1.47477.10.21.11.3.25
		-- 1.3.6.1.4.1.47477.10.21.11.3.25
		link11_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link11OBP 25 }	

--  1.3.6.1.4.1.47477.10.21.11.3.26
		-- 1.3.6.1.4.1.47477.10.21.11.3.26
		link11_PowerAlarmStatus OBJECT-TYPE
			SYNTAX INTEGER
				{
				off(0),
				alarm(1),
				normal(2),
				na(3)
				}
			MAX-ACCESS read-only
			STATUS current
			DESCRIPTION
				"get whether a power alarm is generated."
			::= { link11OBP 26 }	


-- 1.3.6.1.4.1.47477.10.21.11.3.50.1
	link11_WorkModeChange 	OBJECT-TYPE    
    SYNTAX INTEGER	{
				manualMode(0),
				autoMode(1)
		}
	MAX-ACCESS read-only
	STATUS current
    DESCRIPTION
        "The Link mode Changed."
    ::= {link11OBPTrap 1}

-- 1.3.6.1.4.1.47477.10.21.11.3.50.2
	link11_StateChange 	OBJECT-TYPE    
    SYNTAX INTEGER	{
				bypass(0),
				primary(1)
		}
	MAX-ACCESS read-only
	STATUS current
    DESCRIPTION
        "The Link State(Channel) Changed."
    ::= {link11OBPTrap 2}

-- 1.3.6.1.4.1.47477.10.21.11.3.50.3
	link11_R1WaveSet 	OBJECT-TYPE    
    SYNTAX INTEGER	{
				w1310nm(0),
				w1550nm(1)
		}
	MAX-ACCESS read-only
	STATUS current
    DESCRIPTION
        "Set The link11 R1 Wave."
    ::= {link11OBPTrap 3}

-- 1.3.6.1.4.1.47477.10.21.11.3.50.4
	link11_R2WaveSet 	OBJECT-TYPE    
    SYNTAX INTEGER	{
				w1310nm(0),
				w1550nm(1)
		}
	MAX-ACCESS read-only
	STATUS current
    DESCRIPTION
        "Set The link11 R2 Wave."
    ::= {link11OBPTrap 4}			

-- 1.3.6.1.4.1.47477.10.21.11.3.50.5
	link11_R3WaveSet 	OBJECT-TYPE    
    SYNTAX INTEGER	{
				w1310nm(0),
				w1550nm(1)
		}
	MAX-ACCESS read-only
	STATUS current
    DESCRIPTION
        "Set The link11 R3 Wave."
    ::= {link11OBPTrap 5}

-- 1.3.6.1.4.1.47477.10.21.11.3.50.6
	link11_R4WaveSet 	OBJECT-TYPE    
    SYNTAX INTEGER	{
				w1310nm(0),
				w1550nm(1)
		}
	MAX-ACCESS read-only
	STATUS current
    DESCRIPTION
        "Set The link11 R4 Wave."
    ::= {link11OBPTrap 6}	
	
-- 1.3.6.1.4.1.47477.10.21.11.3.50.7
	link11_R1AlarmSet 	OBJECT-TYPE    
    SYNTAX DisplayString
	MAX-ACCESS read-only
	STATUS current
    DESCRIPTION
        "Set The link11 R1 Alarm Threshold."
    ::= {link11OBPTrap 7}

-- 1.3.6.1.4.1.47477.10.21.11.3.50.8
	link11_R2AlarmSet 	OBJECT-TYPE    
    SYNTAX DisplayString
	MAX-ACCESS read-only
	STATUS current
    DESCRIPTION
        "Set The link11 R2 Alarm Threshold."
    ::= {link11OBPTrap 8}
	
-- 1.3.6.1.4.1.47477.10.21.11.3.50.9
	link11_R3AlarmSet 	OBJECT-TYPE    
    SYNTAX DisplayString
	MAX-ACCESS read-only
	STATUS current
    DESCRIPTION
        "Set The link11 R3 Alarm Threshold."
    ::= {link11OBPTrap 9}

-- 1.3.6.1.4.1.47477.10.21.11.3.50.10
	link11_R4AlarmSet 	OBJECT-TYPE    
    SYNTAX DisplayString
	MAX-ACCESS read-only
	STATUS current
    DESCRIPTION
        "Set The link11 R4 Alarm Threshold."
    ::= {link11OBPTrap 10}	
	
	
-- 1.3.6.1.4.1.47477.10.21.11.3.50.11
	link11_1R1AlarmSet 	OBJECT-TYPE    
    SYNTAX DisplayString
	MAX-ACCESS read-only
	STATUS current
    DESCRIPTION
        "Set The link11 1R1 Alarm Threshold."
    ::= {link11OBPTrap 11}

-- 1.3.6.1.4.1.47477.10.21.11.3.50.12
	link11_2R1AlarmSet 	OBJECT-TYPE    
    SYNTAX DisplayString
	MAX-ACCESS read-only
	STATUS current
    DESCRIPTION
        "Set The link11 2R1 Alarm Threshold."
    ::= {link11OBPTrap 12}
	
-- 1.3.6.1.4.1.47477.10.21.11.3.50.13
	link11_1R2AlarmSet 	OBJECT-TYPE    
    SYNTAX DisplayString
	MAX-ACCESS read-only
	STATUS current
    DESCRIPTION
        "Set The link11 1R2 Alarm Threshold."
    ::= {link11OBPTrap 13}

-- 1.3.6.1.4.1.47477.10.21.11.3.50.14
	link11_2R2AlarmSet 	OBJECT-TYPE    
    SYNTAX DisplayString
	MAX-ACCESS read-only
	STATUS current
    DESCRIPTION
        "Set The link11 2R2 Alarm Threshold."
    ::= {link11OBPTrap 14}
	
-- 1.3.6.1.4.1.47477.10.21.11.3.50.15
	link11_1R3AlarmSet 	OBJECT-TYPE    
    SYNTAX DisplayString
	MAX-ACCESS read-only
	STATUS current
    DESCRIPTION
        "Set The link11 1R3 Alarm Threshold."
    ::= {link11OBPTrap 15}

-- 1.3.6.1.4.1.47477.10.21.11.3.50.16
	link11_2R3AlarmSet 	OBJECT-TYPE    
    SYNTAX DisplayString
	MAX-ACCESS read-only
	STATUS current
    DESCRIPTION
        "Set The link11 2R3 Alarm Threshold."
    ::= {link11OBPTrap 16}
	
-- 1.3.6.1.4.1.47477.10.21.11.3.50.17
	link11_1R4AlarmSet 	OBJECT-TYPE    
    SYNTAX DisplayString
	MAX-ACCESS read-only
	STATUS current
    DESCRIPTION
        "Set The link11 1R4 Alarm Threshold."
    ::= {link11OBPTrap 17}

-- 1.3.6.1.4.1.47477.10.21.11.3.50.18
	link11_2R4AlarmSet 	OBJECT-TYPE    
    SYNTAX DisplayString
	MAX-ACCESS read-only
	STATUS current
    DESCRIPTION
        "Set The link11 2R4 Alarm Threshold."
    ::= {link11OBPTrap 18}
	
-- 1.3.6.1.4.1.47477.10.21.11.3.50.19
	link11_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link11 PowerAlarmBypass2 Changed."
    ::= {link11OBPTrap 19}
	
-- 1.3.6.1.4.1.47477.10.21.11.3.50.20
	link11_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link11 PowerAlarmBypass4 Changed."
    ::= {link11OBPTrap 20}	
	
-- 1.3.6.1.4.1.47477.10.21.11.3.50.21
	link11_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link11 PowerAlarmBypass8 Changed."
    ::= {link11OBPTrap 21}
	
-- 1.3.6.1.4.1.47477.10.21.11.3.50.22
	link11_powerAlarmR1 	OBJECT-TYPE    
    SYNTAX DisplayString
	MAX-ACCESS read-only
	STATUS current
    DESCRIPTION
        "Set The link11 R1 Power Status Alarm."
    ::= {link11OBPTrap 22}
	
-- 1.3.6.1.4.1.47477.10.21.11.3.50.23
	link11_powerAlarmR2 	OBJECT-TYPE    
    SYNTAX DisplayString
	MAX-ACCESS read-only
	STATUS current
    DESCRIPTION
        "Set The link11 R2 Power Status Alarm."
    ::= {link11OBPTrap 23}
	
-- 1.3.6.1.4.1.47477.10.21.11.3.50.24
	link11_powerAlarmR3 	OBJECT-TYPE    
    SYNTAX DisplayString
	MAX-ACCESS read-only
	STATUS current
    DESCRIPTION
        "Set The link11 R3 Power Status Alarm."
    ::= {link11OBPTrap 24}
	
-- 1.3.6.1.4.1.47477.10.21.11.3.50.25
	link11_powerAlarmR4 	OBJECT-TYPE    
    SYNTAX DisplayString
	MAX-ACCESS read-only
	STATUS current
    DESCRIPTION
        "Set The link11 R4 Power Status Alarm."
    ::= {link11OBPTrap 25}
	
	
-- 1.3.6.1.4.1.47477.10.21.11.3.50.26
	link11_powerAlarm1R1 	OBJECT-TYPE    
    SYNTAX DisplayString
	MAX-ACCESS read-only
	STATUS current
    DESCRIPTION
        "Set The link11 1R1 Power Status Alarm."
    ::= {link11OBPTrap 26}
	
-- 1.3.6.1.4.1.47477.10.21.11.3.50.27
	link11_powerAlarm2R1 	OBJECT-TYPE    
    SYNTAX DisplayString
	MAX-ACCESS read-only
	STATUS current
    DESCRIPTION
        "Set The link11 2R1 Power Status Alarm."
    ::= {link11OBPTrap 27}
	
-- 1.3.6.1.4.1.47477.10.21.11.3.50.28
	link11_powerAlarm1R2 	OBJECT-TYPE    
    SYNTAX DisplayString
	MAX-ACCESS read-only
	STATUS current
    DESCRIPTION
        "Set The link11 1R2 Power Status Alarm."
    ::= {link11OBPTrap 28}
	
-- 1.3.6.1.4.1.47477.10.21.11.3.50.29
	link11_powerAlarm2R2 	OBJECT-TYPE    
    SYNTAX DisplayString
	MAX-ACCESS read-only
	STATUS current
    DESCRIPTION
        "Set The link11 2R2 Power Status Alarm."
    ::= {link11OBPTrap 29}
	
-- 1.3.6.1.4.1.47477.10.21.11.3.50.30
	link11_powerAlarm1R3 	OBJECT-TYPE    
    SYNTAX DisplayString
	MAX-ACCESS read-only
	STATUS current
    DESCRIPTION
        "Set The link11 1R3 Power Status Alarm."
    ::= {link11OBPTrap 30}
	
-- 1.3.6.1.4.1.47477.10.21.11.3.50.31
	link11_powerAlarm2R3 	OBJECT-TYPE    
    SYNTAX DisplayString
	MAX-ACCESS read-only
	STATUS current
    DESCRIPTION
        "Set The link11 2R1 Power Status Alarm."
    ::= {link11OBPTrap 31}
	
-- 1.3.6.1.4.1.47477.10.21.11.3.50.32
	link11_powerAlarm1R4 	OBJECT-TYPE    
    SYNTAX DisplayString
	MAX-ACCESS read-only
	STATUS current
    DESCRIPTION
        "Set The link11 1R4 Power Status Alarm."
    ::= {link11OBPTrap 32}
	
-- 1.3.6.1.4.1.47477.10.21.11.3.50.33
	link11_powerAlarm2R4 	OBJECT-TYPE    
    SYNTAX DisplayString
	MAX-ACCESS read-only
	STATUS current
    DESCRIPTION
        "Set The link11 2R4 Power Status Alarm."
    ::= {link11OBPTrap 33}
	
--  1.3.6.1.4.1.47477.10.21.12.3.1
		-- 1.3.6.1.4.1.47477.10.21.12.3.1
		link12_State OBJECT-TYPE
			SYNTAX INTEGER
				{
				off(0),
				on(1)
				}
			MAX-ACCESS read-only
			STATUS current
			DESCRIPTION
				"get the information about whether link12 is working."
			::= { link12OBP 1 }

		
--  1.3.6.1.4.1.47477.10.21.12.3.2
		-- 1.3.6.1.4.1.47477.10.21.12.3.2
		link12_DeviceType OBJECT-TYPE
			SYNTAX DisplayString
			MAX-ACCESS read-only
			STATUS current
			DESCRIPTION
				"get the type of card in link12."
			::= { link12OBP 2 }

			
--  1.3.6.1.4.1.47477.10.21.12.3.3
		-- 1.3.6.1.4.1.47477.10.21.12.3.3
		link12_WorkMode OBJECT-TYPE
			SYNTAX INTEGER
				{
				manualMode(0),
				autoMode(1)
				}
			MAX-ACCESS read-write
			STATUS current
			DESCRIPTION
				"get or set link12's work mode."
			::= { link12OBP 3 }

		
--  1.3.6.1.4.1.47477.10.21.12.3.4
		-- 1.3.6.1.4.1.47477.10.21.12.3.4
		link12_Channel OBJECT-TYPE
			SYNTAX INTEGER
				{
				bypass(0),
				primary(1)
				}
			MAX-ACCESS read-write
			STATUS current
			DESCRIPTION
				"get or set the channel in which link12 works."
			::= { link12OBP 4 }


--  1.3.6.1.4.1.47477.10.21.12.3.5
		-- 1.3.6.1.4.1.47477.10.21.12.3.5
		link12_R1Power OBJECT-TYPE
			SYNTAX DisplayString
			MAX-ACCESS read-only
			STATUS current
			DESCRIPTION
				"get the power of R1 in link12."
			::= { link12OBP 5 }

		
--  1.3.6.1.4.1.47477.10.21.12.3.6
		-- 1.3.6.1.4.1.47477.10.21.12.3.6
		link12_R2Power OBJECT-TYPE
			SYNTAX DisplayString
			MAX-ACCESS read-only
			STATUS current
			DESCRIPTION
				"get the power of R2 in link12."
			::= { link12OBP 6 }
			
--  1.3.6.1.4.1.47477.10.21.12.3.35
		-- 1.3.6.1.4.1.47477.10.21.12.3.35
		link12_R3Power OBJECT-TYPE
			SYNTAX DisplayString
			MAX-ACCESS read-only
			STATUS current
			DESCRIPTION
				"get the power of R3 in link12."
			::= { link12OBP 35 }
			
--  1.3.6.1.4.1.47477.10.21.12.3.36
		-- 1.3.6.1.4.1.47477.10.21.12.3.36
		link12_R4Power OBJECT-TYPE
			SYNTAX DisplayString
			MAX-ACCESS read-only
			STATUS current
			DESCRIPTION
				"get the power of R4 in link12."
			::= { link12OBP 36 }		
		
--  1.3.6.1.4.1.47477.10.21.12.3.7
		-- 1.3.6.1.4.1.47477.10.21.12.3.7
		link12_R1Wave OBJECT-TYPE
			SYNTAX INTEGER
				{
				w1310nm(0),
				w1550nm(1),
				na(2)
				}
			MAX-ACCESS read-write
			STATUS current
			DESCRIPTION
				"get or set the wave length of R1 in link12."
			::= { link12OBP 7 }

		
--  1.3.6.1.4.1.47477.10.21.12.3.8
		-- 1.3.6.1.4.1.47477.10.21.12.3.8
		link12_R2Wave OBJECT-TYPE
			SYNTAX INTEGER
				{
				w1310nm(0),
				w1550nm(1),
				na(2)
				}
			MAX-ACCESS read-write
			STATUS current
			DESCRIPTION
				"get or set the wave length of R2 in link12."
			::= { link12OBP 8 }


--  1.3.6.1.4.1.47477.10.21.12.3.27
		-- 1.3.6.1.4.1.47477.10.21.12.3.27
		link12_R3Wave OBJECT-TYPE
			SYNTAX INTEGER
				{
				w1310nm(0),
				w1550nm(1),
				na(2)
				}
			MAX-ACCESS read-write
			STATUS current
			DESCRIPTION
				"get or set the wave length of R3 in link12."
			::= { link12OBP 27 }

		
--  1.3.6.1.4.1.47477.10.21.12.3.28
		-- 1.3.6.1.4.1.47477.10.21.12.3.28
		link12_R4Wave OBJECT-TYPE
			SYNTAX INTEGER
				{
				w1310nm(0),
				w1550nm(1),
				na(2)
				}
			MAX-ACCESS read-write
			STATUS current
			DESCRIPTION
				"get or set the wave length of R4 in link12."
			::= { link12OBP 28 }
			
--  1.3.6.1.4.1.47477.10.21.12.3.9
		-- 1.3.6.1.4.1.47477.10.21.12.3.9
		link12_R1AlarmPower OBJECT-TYPE
			SYNTAX DisplayString
			MAX-ACCESS read-write
			STATUS current
			DESCRIPTION
				"get or set the power alarm threshold of R1 in link12."
			::= { link12OBP 9 }

		
--  1.3.6.1.4.1.47477.10.21.12.3.10
		-- 1.3.6.1.4.1.47477.10.21.12.3.10
		link12_R2AlarmPower OBJECT-TYPE
			SYNTAX DisplayString
			MAX-ACCESS read-write
			STATUS current
			DESCRIPTION
				"get or set the power alarm threshold of R2 in link12."
			::= { link12OBP 10 }


--  1.3.6.1.4.1.47477.10.21.12.3.29
		-- 1.3.6.1.4.1.47477.10.21.12.3.29
		link12_R3AlarmPower OBJECT-TYPE
			SYNTAX DisplayString
			MAX-ACCESS read-write
			STATUS current
			DESCRIPTION
				"get or set the power alarm threshold of R3 in link12."
			::= { link12OBP 29 }

		
--  1.3.6.1.4.1.47477.10.21.12.3.30
		-- 1.3.6.1.4.1.47477.10.21.12.3.30
		link12_R4AlarmPower OBJECT-TYPE
			SYNTAX DisplayString
			MAX-ACCESS read-write
			STATUS current
			DESCRIPTION
				"get or set the power alarm threshold of R4 in link12."
			::= { link12OBP 30 }

-- OBP4
--  1.3.6.1.4.1.47477.10.21.12.3.37
		-- 1.3.6.1.4.1.47477.10.21.12.3.37
		link12_1R1Power OBJECT-TYPE
			SYNTAX DisplayString
			MAX-ACCESS read-only
			STATUS current
			DESCRIPTION
				"get the power of 1R1 in link12."
			::= { link12OBP 37 }
			
--  1.3.6.1.4.1.47477.10.21.12.3.38
		-- 1.3.6.1.4.1.47477.10.21.12.3.38
		link12_1R2Power OBJECT-TYPE
			SYNTAX DisplayString
			MAX-ACCESS read-only
			STATUS current
			DESCRIPTION
				"get the power of 1R2 in link12."
			::= { link12OBP 38 }

--  1.3.6.1.4.1.47477.10.21.12.3.39
		-- 1.3.6.1.4.1.47477.10.21.12.3.39
		link12_1R3Power OBJECT-TYPE
			SYNTAX DisplayString
			MAX-ACCESS read-only
			STATUS current
			DESCRIPTION
				"get the power of 1R3 in link12."
			::= { link12OBP 39 }
			
--  1.3.6.1.4.1.47477.10.21.12.3.40
		-- 1.3.6.1.4.1.47477.10.21.12.3.40
		link12_1R4Power OBJECT-TYPE
			SYNTAX DisplayString
			MAX-ACCESS read-only
			STATUS current
			DESCRIPTION
				"get the power of 1R4 in link12."
			::= { link12OBP 40 }

--  1.3.6.1.4.1.47477.10.21.12.3.41
		-- 1.3.6.1.4.1.47477.10.21.12.3.41
		link12_2R1Power OBJECT-TYPE
			SYNTAX DisplayString
			MAX-ACCESS read-only
			STATUS current
			DESCRIPTION
				"get the power of 2R1 in link12."
			::= { link12OBP 41 }
			
--  1.3.6.1.4.1.47477.10.21.12.3.42
		-- 1.3.6.1.4.1.47477.10.21.12.3.42
		link12_2R2Power OBJECT-TYPE
			SYNTAX DisplayString
			MAX-ACCESS read-only
			STATUS current
			DESCRIPTION
				"get the power of 2R2 in link12."
			::= { link12OBP 42 }

--  1.3.6.1.4.1.47477.10.21.12.3.41
		-- 1.3.6.1.4.1.47477.10.21.12.3.43
		link12_2R3Power OBJECT-TYPE
			SYNTAX DisplayString
			MAX-ACCESS read-only
			STATUS current
			DESCRIPTION
				"get the power of 2R3 in link12."
			::= { link12OBP 43 }
			
--  1.3.6.1.4.1.47477.10.21.12.3.42
		-- 1.3.6.1.4.1.47477.10.21.12.3.44
		link12_2R4Power OBJECT-TYPE
			SYNTAX DisplayString
			MAX-ACCESS read-only
			STATUS current
			DESCRIPTION
				"get the power of 2R4 in link12."
			::= { link12OBP 44 }
			
--  1.3.6.1.4.1.47477.10.21.12.3.49
		-- 1.3.6.1.4.1.47477.10.21.12.3.49
		link12_1R1Wave OBJECT-TYPE
			SYNTAX INTEGER
				{
				w850nm(0),
				na(2)
				}
			MAX-ACCESS read-only
			STATUS current
			DESCRIPTION
				"get the wave length of 1R1 in link12."
			::= { link12OBP 49 }
		
--  1.3.6.1.4.1.47477.10.21.12.3.60
		-- 1.3.6.1.4.1.47477.10.21.12.3.60
		link12_1R2Wave OBJECT-TYPE
			SYNTAX INTEGER
				{
				w850nm(0),
				na(2)
				}
			MAX-ACCESS read-only
			STATUS current
			DESCRIPTION
				"get the wave length of 1R2 in link12."
			::= { link12OBP 60 }

--  1.3.6.1.4.1.47477.10.21.12.3.61
		-- 1.3.6.1.4.1.47477.10.21.12.3.61
		link12_1R3Wave OBJECT-TYPE
			SYNTAX INTEGER
				{
				w850nm(0),
				na(2)
				}
			MAX-ACCESS read-only
			STATUS current
			DESCRIPTION
				"get the wave length of 1R3 in link12."
			::= { link12OBP 61 }

		
--  1.3.6.1.4.1.47477.10.21.12.3.62
		-- 1.3.6.1.4.1.47477.10.21.12.3.62
		link12_1R4Wave OBJECT-TYPE
			SYNTAX INTEGER
				{
				w850nm(0),
				na(2)
				}
			MAX-ACCESS read-only
			STATUS current
			DESCRIPTION
				"get the wave length of 1R4 in link12."
			::= { link12OBP 62 }
	
--  1.3.6.1.4.1.47477.10.21.12.3.63
		-- 1.3.6.1.4.1.47477.10.21.12.3.63
		link12_2R1Wave OBJECT-TYPE
			SYNTAX INTEGER
				{
				w850nm(0),
				na(2)
				}
			MAX-ACCESS read-only
			STATUS current
			DESCRIPTION
				"get the wave length of 2R1 in link12."
			::= { link12OBP 63 }

		
--  1.3.6.1.4.1.47477.10.21.12.3.64
		-- 1.3.6.1.4.1.47477.10.21.12.3.64
		link12_2R2Wave OBJECT-TYPE
			SYNTAX INTEGER
				{
				w850nm(0),
				na(2)
				}
			MAX-ACCESS read-only
			STATUS current
			DESCRIPTION
				"get the wave length of 2R2 in link12."
			::= { link12OBP 64 }	
	
--  1.3.6.1.4.1.47477.10.21.12.3.65
		-- 1.3.6.1.4.1.47477.10.21.12.3.65
		link12_2R3Wave OBJECT-TYPE
			SYNTAX INTEGER
				{
				w850nm(0),
				na(2)
				}
			MAX-ACCESS read-only
			STATUS current
			DESCRIPTION
				"get the wave length of 2R3 in link12."
			::= { link12OBP 65 }

		
--  1.3.6.1.4.1.47477.10.21.12.3.66
		-- 1.3.6.1.4.1.47477.10.21.12.3.66
		link12_2R4Wave OBJECT-TYPE
			SYNTAX INTEGER
				{
				w850nm(0),
				na(2)
				}
			MAX-ACCESS read-only
			STATUS current
			DESCRIPTION
				"get the wave length of 2R4 in link12."
			::= { link12OBP 66 }	
			
--  1.3.6.1.4.1.47477.10.21.12.3.31
		-- 1.3.6.1.4.1.47477.10.21.12.3.31
		link12_1R1AlarmPower OBJECT-TYPE
			SYNTAX DisplayString
			MAX-ACCESS read-write
			STATUS current
			DESCRIPTION
				"get or set the power alarm threshold of 1R1 in link12."
			::= { link12OBP 31 }
			
--  1.3.6.1.4.1.47477.10.21.12.3.32
		-- 1.3.6.1.4.1.47477.10.21.12.3.32
		link12_1R2AlarmPower OBJECT-TYPE
			SYNTAX DisplayString
			MAX-ACCESS read-write
			STATUS current
			DESCRIPTION
				"get or set the power alarm threshold of 1R2 in link12."
			::= { link12OBP 32 }

--  1.3.6.1.4.1.47477.10.21.12.3.33
		-- 1.3.6.1.4.1.47477.10.21.12.3.33
		link12_1R3AlarmPower OBJECT-TYPE
			SYNTAX DisplayString
			MAX-ACCESS read-write
			STATUS current
			DESCRIPTION
				"get or set the power alarm threshold of 1R3 in link12."
			::= { link12OBP 33 }
			
--  1.3.6.1.4.1.47477.10.21.12.3.34
		-- 1.3.6.1.4.1.47477.10.21.12.3.34
		link12_1R4AlarmPower OBJECT-TYPE
			SYNTAX DisplayString
			MAX-ACCESS read-write
			STATUS current
			DESCRIPTION
				"get or set the power alarm threshold of 1R4 in link12."
			::= { link12OBP 34 }

--  1.3.6.1.4.1.47477.10.21.12.3.45
		-- 1.3.6.1.4.1.47477.10.21.12.3.45
		link12_2R1AlarmPower OBJECT-TYPE
			SYNTAX DisplayString
			MAX-ACCESS read-write
			STATUS current
			DESCRIPTION
				"get or set the power alarm threshold of 2R1 in link12."
			::= { link12OBP 45 }
			
--  1.3.6.1.4.1.47477.10.21.12.3.46
		-- 1.3.6.1.4.1.47477.10.21.12.3.46
		link12_2R2AlarmPower OBJECT-TYPE
			SYNTAX DisplayString
			MAX-ACCESS read-write
			STATUS current
			DESCRIPTION
				"get or set the power alarm threshold of 2R2 in link12."
			::= { link12OBP 46 }

--  1.3.6.1.4.1.47477.10.21.12.3.47
		-- 1.3.6.1.4.1.47477.10.21.12.3.47
		link12_2R3AlarmPower OBJECT-TYPE
			SYNTAX DisplayString
			MAX-ACCESS read-write
			STATUS current
			DESCRIPTION
				"get or set the power alarm threshold of 2R3 in link12."
			::= { link12OBP 47 }
			
--  1.3.6.1.4.1.47477.10.21.12.3.48
		-- 1.3.6.1.4.1.47477.10.21.12.3.48
		link12_2R4AlarmPower OBJECT-TYPE
			SYNTAX DisplayString
			MAX-ACCESS read-write
			STATUS current
			DESCRIPTION
				"get or set the power alarm threshold of 2R4 in link12."
			::= { link12OBP 48 }
			
--  1.3.6.1.4.1.47477.10.21.12.3.11
		-- 1.3.6.1.4.1.47477.10.21.12.3.11
		link12_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link12OBP 11 }
			
--  1.3.6.1.4.1.47477.10.21.12.3.67
		-- 1.3.6.1.4.1.47477.10.21.12.3.67
		link12_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link12OBP 67 }
			
--  1.3.6.1.4.1.47477.10.21.12.3.68
		-- 1.3.6.1.4.1.47477.10.21.12.3.68
		link12_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link12OBP 68 }
			
--  1.3.6.1.4.1.47477.10.21.12.3.12
		-- 1.3.6.1.4.1.47477.10.21.12.3.12
		link12_ReturnDelay OBJECT-TYPE
			--SYNTAX Integer32
			SYNTAX Integer32
			MAX-ACCESS read-write
			STATUS current
			DESCRIPTION
				"get or set how long link12 takes to return to automatic mode."
			::= { link12OBP 12 }
			
--  1.3.6.1.4.1.47477.10.21.12.3.13
		-- 1.3.6.1.4.1.47477.10.21.12.3.13
		link12_BackMode OBJECT-TYPE
			SYNTAX INTEGER
				{
				autoNoBack(0),
				autoBack(1)
				}
			MAX-ACCESS read-write
			STATUS current
			DESCRIPTION
				"get or set the back mode of link12."
			::= { link12OBP 13 }

		
--  1.3.6.1.4.1.47477.10.21.12.3.14
		-- 1.3.6.1.4.1.47477.10.21.12.3.14
		link12_BackDelay OBJECT-TYPE
			SYNTAX Integer32
			MAX-ACCESS read-write
			STATUS current
			DESCRIPTION
				"get or set the back delay."
			::= { link12OBP 14 }

--  1.3.6.1.4.1.47477.10.21.12.3.15
		-- 1.3.6.1.4.1.47477.10.21.12.3.15
		link12_ActiveHeartSwitch OBJECT-TYPE
			SYNTAX INTEGER
				{
				off(0),
				on(1)
				}
			MAX-ACCESS read-write
			STATUS current
			DESCRIPTION
				"get or set the switch status of active heartbeat."
			::= { link12OBP 15 }

		
--  1.3.6.1.4.1.47477.10.21.12.3.16
		-- 1.3.6.1.4.1.47477.10.21.12.3.16
		link12_ActiveSendInterval OBJECT-TYPE
			SYNTAX Integer32
			MAX-ACCESS read-write
			STATUS current
			DESCRIPTION
				"get or set the send interval of active heartbeat."
			::= { link12OBP 16 }		

--  1.3.6.1.4.1.47477.10.21.12.3.17
		-- 1.3.6.1.4.1.47477.10.21.12.3.17
		link12_ActiveTimeOut OBJECT-TYPE
			SYNTAX Integer32
			MAX-ACCESS read-write
			STATUS current
			DESCRIPTION
				"get or set how long the active heartbeat send timeout."
			::= { link12OBP 17 }

--  1.3.6.1.4.1.47477.10.21.12.3.18
		-- 1.3.6.1.4.1.47477.10.21.12.3.18
		link12_ActiveLossBypass OBJECT-TYPE
			SYNTAX Integer32
			MAX-ACCESS read-write
			STATUS current
			DESCRIPTION
				"get or set the bypass for active heartbeat packet loss."
			::= { link12OBP 18 }

--  1.3.6.1.4.1.47477.10.21.12.3.19
		-- 1.3.6.1.4.1.47477.10.21.12.3.19
		link12_PingIpAddress OBJECT-TYPE
			SYNTAX IpAddress
			MAX-ACCESS read-write
			STATUS current
			DESCRIPTION
				"get or set the ping ip address of link12."
			::= { link12OBP 19 }

--  1.3.6.1.4.1.47477.10.21.12.3.20
		-- 1.3.6.1.4.1.47477.10.21.12.3.20
		link12_PassiveHeartSwitch OBJECT-TYPE
			SYNTAX INTEGER
				{
				off(0),
				on(1)
				}
			MAX-ACCESS read-write
			STATUS current
			DESCRIPTION
				"get or set the switch status of passive heartbeat."
			::= { link12OBP 20 }
	

--  1.3.6.1.4.1.47477.10.21.12.3.21
		-- 1.3.6.1.4.1.47477.10.21.12.3.21
		link12_PassiveTimeOut OBJECT-TYPE
			SYNTAX Integer32
			MAX-ACCESS read-write
			STATUS current
			DESCRIPTION
				"get or set how long the passive heartbeat send timeout."
			::= { link12OBP 21 }

--  1.3.6.1.4.1.47477.10.21.12.3.22
		-- 1.3.6.1.4.1.47477.10.21.12.3.22
		link12_PassiveLossBypass OBJECT-TYPE
			SYNTAX Integer32
			MAX-ACCESS read-write
			STATUS current
			DESCRIPTION
				"get or set the bypass for passive heartbeat packet loss."
			::= { link12OBP 22 }

--  1.3.6.1.4.1.47477.10.21.12.3.23
		-- 1.3.6.1.4.1.47477.10.21.12.3.23
		link12_SwitchProtect OBJECT-TYPE
			SYNTAX INTEGER
				{
				off(0),
				on(1)
				}
			MAX-ACCESS read-write
			STATUS current
			DESCRIPTION
				"get or set the switch protection status of link12."
			::= { link12OBP 23 }
			
--  1.3.6.1.4.1.47477.10.21.12.3.24
		-- 1.3.6.1.4.1.47477.10.21.12.3.24
		link12_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link12OBP 24 }		

--  1.3.6.1.4.1.47477.10.21.12.3.25
		-- 1.3.6.1.4.1.47477.10.21.12.3.25
		link12_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link12OBP 25 }	

--  1.3.6.1.4.1.47477.10.21.12.3.26
		-- 1.3.6.1.4.1.47477.10.21.12.3.26
		link12_PowerAlarmStatus OBJECT-TYPE
			SYNTAX INTEGER
				{
				off(0),
				alarm(1),
				normal(2),
				na(3)
				}
			MAX-ACCESS read-only
			STATUS current
			DESCRIPTION
				"get whether a power alarm is generated."
			::= { link12OBP 26 }	


-- 1.3.6.1.4.1.47477.10.21.12.3.50.1
	link12_WorkModeChange 	OBJECT-TYPE    
    SYNTAX INTEGER	{
				manualMode(0),
				autoMode(1)
		}
	MAX-ACCESS read-only
	STATUS current
    DESCRIPTION
        "The Link mode Changed."
    ::= {link12OBPTrap 1}

-- 1.3.6.1.4.1.47477.10.21.12.3.50.2
	link12_StateChange 	OBJECT-TYPE    
    SYNTAX INTEGER	{
				bypass(0),
				primary(1)
		}
	MAX-ACCESS read-only
	STATUS current
    DESCRIPTION
        "The Link State(Channel) Changed."
    ::= {link12OBPTrap 2}

-- 1.3.6.1.4.1.47477.10.21.12.3.50.3
	link12_R1WaveSet 	OBJECT-TYPE    
    SYNTAX INTEGER	{
				w1310nm(0),
				w1550nm(1)
		}
	MAX-ACCESS read-only
	STATUS current
    DESCRIPTION
        "Set The link12 R1 Wave."
    ::= {link12OBPTrap 3}

-- 1.3.6.1.4.1.47477.10.21.12.3.50.4
	link12_R2WaveSet 	OBJECT-TYPE    
    SYNTAX INTEGER	{
				w1310nm(0),
				w1550nm(1)
		}
	MAX-ACCESS read-only
	STATUS current
    DESCRIPTION
        "Set The link12 R2 Wave."
    ::= {link12OBPTrap 4}			

-- 1.3.6.1.4.1.47477.10.21.12.3.50.5
	link12_R3WaveSet 	OBJECT-TYPE    
    SYNTAX INTEGER	{
				w1310nm(0),
				w1550nm(1)
		}
	MAX-ACCESS read-only
	STATUS current
    DESCRIPTION
        "Set The link12 R3 Wave."
    ::= {link12OBPTrap 5}

-- 1.3.6.1.4.1.47477.10.21.12.3.50.6
	link12_R4WaveSet 	OBJECT-TYPE    
    SYNTAX INTEGER	{
				w1310nm(0),
				w1550nm(1)
		}
	MAX-ACCESS read-only
	STATUS current
    DESCRIPTION
        "Set The link12 R4 Wave."
    ::= {link12OBPTrap 6}	
	
-- 1.3.6.1.4.1.47477.10.21.12.3.50.7
	link12_R1AlarmSet 	OBJECT-TYPE    
    SYNTAX DisplayString
	MAX-ACCESS read-only
	STATUS current
    DESCRIPTION
        "Set The link12 R1 Alarm Threshold."
    ::= {link12OBPTrap 7}

-- 1.3.6.1.4.1.47477.10.21.12.3.50.8
	link12_R2AlarmSet 	OBJECT-TYPE    
    SYNTAX DisplayString
	MAX-ACCESS read-only
	STATUS current
    DESCRIPTION
        "Set The link12 R2 Alarm Threshold."
    ::= {link12OBPTrap 8}
	
-- 1.3.6.1.4.1.47477.10.21.12.3.50.9
	link12_R3AlarmSet 	OBJECT-TYPE    
    SYNTAX DisplayString
	MAX-ACCESS read-only
	STATUS current
    DESCRIPTION
        "Set The link12 R3 Alarm Threshold."
    ::= {link12OBPTrap 9}

-- 1.3.6.1.4.1.47477.10.21.12.3.50.10
	link12_R4AlarmSet 	OBJECT-TYPE    
    SYNTAX DisplayString
	MAX-ACCESS read-only
	STATUS current
    DESCRIPTION
        "Set The link12 R4 Alarm Threshold."
    ::= {link12OBPTrap 10}	
	
	
-- 1.3.6.1.4.1.47477.10.21.12.3.50.11
	link12_1R1AlarmSet 	OBJECT-TYPE    
    SYNTAX DisplayString
	MAX-ACCESS read-only
	STATUS current
    DESCRIPTION
        "Set The link12 1R1 Alarm Threshold."
    ::= {link12OBPTrap 11}

-- 1.3.6.1.4.1.47477.10.21.12.3.50.12
	link12_2R1AlarmSet 	OBJECT-TYPE    
    SYNTAX DisplayString
	MAX-ACCESS read-only
	STATUS current
    DESCRIPTION
        "Set The link12 2R1 Alarm Threshold."
    ::= {link12OBPTrap 12}
	
-- 1.3.6.1.4.1.47477.10.21.12.3.50.13
	link12_1R2AlarmSet 	OBJECT-TYPE    
    SYNTAX DisplayString
	MAX-ACCESS read-only
	STATUS current
    DESCRIPTION
        "Set The link12 1R2 Alarm Threshold."
    ::= {link12OBPTrap 13}

-- 1.3.6.1.4.1.47477.10.21.12.3.50.14
	link12_2R2AlarmSet 	OBJECT-TYPE    
    SYNTAX DisplayString
	MAX-ACCESS read-only
	STATUS current
    DESCRIPTION
        "Set The link12 2R2 Alarm Threshold."
    ::= {link12OBPTrap 14}
	
-- 1.3.6.1.4.1.47477.10.21.12.3.50.15
	link12_1R3AlarmSet 	OBJECT-TYPE    
    SYNTAX DisplayString
	MAX-ACCESS read-only
	STATUS current
    DESCRIPTION
        "Set The link12 1R3 Alarm Threshold."
    ::= {link12OBPTrap 15}

-- 1.3.6.1.4.1.47477.10.21.12.3.50.16
	link12_2R3AlarmSet 	OBJECT-TYPE    
    SYNTAX DisplayString
	MAX-ACCESS read-only
	STATUS current
    DESCRIPTION
        "Set The link12 2R3 Alarm Threshold."
    ::= {link12OBPTrap 16}
	
-- 1.3.6.1.4.1.47477.10.21.12.3.50.17
	link12_1R4AlarmSet 	OBJECT-TYPE    
    SYNTAX DisplayString
	MAX-ACCESS read-only
	STATUS current
    DESCRIPTION
        "Set The link12 1R4 Alarm Threshold."
    ::= {link12OBPTrap 17}

-- 1.3.6.1.4.1.47477.10.21.12.3.50.18
	link12_2R4AlarmSet 	OBJECT-TYPE    
    SYNTAX DisplayString
	MAX-ACCESS read-only
	STATUS current
    DESCRIPTION
        "Set The link12 2R4 Alarm Threshold."
    ::= {link12OBPTrap 18}
	
-- 1.3.6.1.4.1.47477.10.21.12.3.50.19
	link12_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link12 PowerAlarmBypass2 Changed."
    ::= {link12OBPTrap 19}
	
-- 1.3.6.1.4.1.47477.10.21.12.3.50.20
	link12_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link12 PowerAlarmBypass4 Changed."
    ::= {link12OBPTrap 20}	
	
-- 1.3.6.1.4.1.47477.10.21.12.3.50.21
	link12_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link12 PowerAlarmBypass8 Changed."
    ::= {link12OBPTrap 21}
	
-- 1.3.6.1.4.1.47477.10.21.12.3.50.22
	link12_powerAlarmR1 	OBJECT-TYPE    
    SYNTAX DisplayString
	MAX-ACCESS read-only
	STATUS current
    DESCRIPTION
        "Set The link12 R1 Power Status Alarm."
    ::= {link12OBPTrap 22}
	
-- 1.3.6.1.4.1.47477.10.21.12.3.50.23
	link12_powerAlarmR2 	OBJECT-TYPE    
    SYNTAX DisplayString
	MAX-ACCESS read-only
	STATUS current
    DESCRIPTION
        "Set The link12 R2 Power Status Alarm."
    ::= {link12OBPTrap 23}
	
-- 1.3.6.1.4.1.47477.10.21.12.3.50.24
	link12_powerAlarmR3 	OBJECT-TYPE    
    SYNTAX DisplayString
	MAX-ACCESS read-only
	STATUS current
    DESCRIPTION
        "Set The link12 R3 Power Status Alarm."
    ::= {link12OBPTrap 24}
	
-- 1.3.6.1.4.1.47477.10.21.12.3.50.25
	link12_powerAlarmR4 	OBJECT-TYPE    
    SYNTAX DisplayString
	MAX-ACCESS read-only
	STATUS current
    DESCRIPTION
        "Set The link12 R4 Power Status Alarm."
    ::= {link12OBPTrap 25}
	
	
-- 1.3.6.1.4.1.47477.10.21.12.3.50.26
	link12_powerAlarm1R1 	OBJECT-TYPE    
    SYNTAX DisplayString
	MAX-ACCESS read-only
	STATUS current
    DESCRIPTION
        "Set The link12 1R1 Power Status Alarm."
    ::= {link12OBPTrap 26}
	
-- 1.3.6.1.4.1.47477.10.21.12.3.50.27
	link12_powerAlarm2R1 	OBJECT-TYPE    
    SYNTAX DisplayString
	MAX-ACCESS read-only
	STATUS current
    DESCRIPTION
        "Set The link12 2R1 Power Status Alarm."
    ::= {link12OBPTrap 27}
	
-- 1.3.6.1.4.1.47477.10.21.12.3.50.28
	link12_powerAlarm1R2 	OBJECT-TYPE    
    SYNTAX DisplayString
	MAX-ACCESS read-only
	STATUS current
    DESCRIPTION
        "Set The link12 1R2 Power Status Alarm."
    ::= {link12OBPTrap 28}
	
-- 1.3.6.1.4.1.47477.10.21.12.3.50.29
	link12_powerAlarm2R2 	OBJECT-TYPE    
    SYNTAX DisplayString
	MAX-ACCESS read-only
	STATUS current
    DESCRIPTION
        "Set The link12 2R2 Power Status Alarm."
    ::= {link12OBPTrap 29}
	
-- 1.3.6.1.4.1.47477.10.21.12.3.50.30
	link12_powerAlarm1R3 	OBJECT-TYPE    
    SYNTAX DisplayString
	MAX-ACCESS read-only
	STATUS current
    DESCRIPTION
        "Set The link12 1R3 Power Status Alarm."
    ::= {link12OBPTrap 30}
	
-- 1.3.6.1.4.1.47477.10.21.12.3.50.31
	link12_powerAlarm2R3 	OBJECT-TYPE    
    SYNTAX DisplayString
	MAX-ACCESS read-only
	STATUS current
    DESCRIPTION
        "Set The link12 2R1 Power Status Alarm."
    ::= {link12OBPTrap 31}
	
-- 1.3.6.1.4.1.47477.10.21.12.3.50.32
	link12_powerAlarm1R4 	OBJECT-TYPE    
    SYNTAX DisplayString
	MAX-ACCESS read-only
	STATUS current
    DESCRIPTION
        "Set The link12 1R4 Power Status Alarm."
    ::= {link12OBPTrap 32}
	
-- 1.3.6.1.4.1.47477.10.21.12.3.50.33
	link12_powerAlarm2R4 	OBJECT-TYPE    
    SYNTAX DisplayString
	MAX-ACCESS read-only
	STATUS current
    DESCRIPTION
        "Set The link12 2R4 Power Status Alarm."
    ::= {link12OBPTrap 33}
	
--  1.3.6.1.4.1.47477.10.21.13.3.1
		-- 1.3.6.1.4.1.47477.10.21.13.3.1
		link13_State OBJECT-TYPE
			SYNTAX INTEGER
				{
				off(0),
				on(1)
				}
			MAX-ACCESS read-only
			STATUS current
			DESCRIPTION
				"get the information about whether link13 is working."
			::= { link13OBP 1 }

		
--  1.3.6.1.4.1.47477.10.21.13.3.2
		-- 1.3.6.1.4.1.47477.10.21.13.3.2
		link13_DeviceType OBJECT-TYPE
			SYNTAX DisplayString
			MAX-ACCESS read-only
			STATUS current
			DESCRIPTION
				"get the type of card in link13."
			::= { link13OBP 2 }

			
--  1.3.6.1.4.1.47477.10.21.13.3.3
		-- 1.3.6.1.4.1.47477.10.21.13.3.3
		link13_WorkMode OBJECT-TYPE
			SYNTAX INTEGER
				{
				manualMode(0),
				autoMode(1)
				}
			MAX-ACCESS read-write
			STATUS current
			DESCRIPTION
				"get or set link13's work mode."
			::= { link13OBP 3 }

		
--  1.3.6.1.4.1.47477.10.21.13.3.4
		-- 1.3.6.1.4.1.47477.10.21.13.3.4
		link13_Channel OBJECT-TYPE
			SYNTAX INTEGER
				{
				bypass(0),
				primary(1)
				}
			MAX-ACCESS read-write
			STATUS current
			DESCRIPTION
				"get or set the channel in which link13 works."
			::= { link13OBP 4 }


--  1.3.6.1.4.1.47477.10.21.13.3.5
		-- 1.3.6.1.4.1.47477.10.21.13.3.5
		link13_R1Power OBJECT-TYPE
			SYNTAX DisplayString
			MAX-ACCESS read-only
			STATUS current
			DESCRIPTION
				"get the power of R1 in link13."
			::= { link13OBP 5 }

		
--  1.3.6.1.4.1.47477.10.21.13.3.6
		-- 1.3.6.1.4.1.47477.10.21.13.3.6
		link13_R2Power OBJECT-TYPE
			SYNTAX DisplayString
			MAX-ACCESS read-only
			STATUS current
			DESCRIPTION
				"get the power of R2 in link13."
			::= { link13OBP 6 }
			
--  1.3.6.1.4.1.47477.10.21.13.3.35
		-- 1.3.6.1.4.1.47477.10.21.13.3.35
		link13_R3Power OBJECT-TYPE
			SYNTAX DisplayString
			MAX-ACCESS read-only
			STATUS current
			DESCRIPTION
				"get the power of R3 in link13."
			::= { link13OBP 35 }
			
--  1.3.6.1.4.1.47477.10.21.13.3.36
		-- 1.3.6.1.4.1.47477.10.21.13.3.36
		link13_R4Power OBJECT-TYPE
			SYNTAX DisplayString
			MAX-ACCESS read-only
			STATUS current
			DESCRIPTION
				"get the power of R4 in link13."
			::= { link13OBP 36 }		
		
--  1.3.6.1.4.1.47477.10.21.13.3.7
		-- 1.3.6.1.4.1.47477.10.21.13.3.7
		link13_R1Wave OBJECT-TYPE
			SYNTAX INTEGER
				{
				w1310nm(0),
				w1550nm(1),
				na(2)
				}
			MAX-ACCESS read-write
			STATUS current
			DESCRIPTION
				"get or set the wave length of R1 in link13."
			::= { link13OBP 7 }

		
--  1.3.6.1.4.1.47477.10.21.13.3.8
		-- 1.3.6.1.4.1.47477.10.21.13.3.8
		link13_R2Wave OBJECT-TYPE
			SYNTAX INTEGER
				{
				w1310nm(0),
				w1550nm(1),
				na(2)
				}
			MAX-ACCESS read-write
			STATUS current
			DESCRIPTION
				"get or set the wave length of R2 in link13."
			::= { link13OBP 8 }


--  1.3.6.1.4.1.47477.10.21.13.3.27
		-- 1.3.6.1.4.1.47477.10.21.13.3.27
		link13_R3Wave OBJECT-TYPE
			SYNTAX INTEGER
				{
				w1310nm(0),
				w1550nm(1),
				na(2)
				}
			MAX-ACCESS read-write
			STATUS current
			DESCRIPTION
				"get or set the wave length of R3 in link13."
			::= { link13OBP 27 }

		
--  1.3.6.1.4.1.47477.10.21.13.3.28
		-- 1.3.6.1.4.1.47477.10.21.13.3.28
		link13_R4Wave OBJECT-TYPE
			SYNTAX INTEGER
				{
				w1310nm(0),
				w1550nm(1),
				na(2)
				}
			MAX-ACCESS read-write
			STATUS current
			DESCRIPTION
				"get or set the wave length of R4 in link13."
			::= { link13OBP 28 }
			
--  1.3.6.1.4.1.47477.10.21.13.3.9
		-- 1.3.6.1.4.1.47477.10.21.13.3.9
		link13_R1AlarmPower OBJECT-TYPE
			SYNTAX DisplayString
			MAX-ACCESS read-write
			STATUS current
			DESCRIPTION
				"get or set the power alarm threshold of R1 in link13."
			::= { link13OBP 9 }

		
--  1.3.6.1.4.1.47477.10.21.13.3.10
		-- 1.3.6.1.4.1.47477.10.21.13.3.10
		link13_R2AlarmPower OBJECT-TYPE
			SYNTAX DisplayString
			MAX-ACCESS read-write
			STATUS current
			DESCRIPTION
				"get or set the power alarm threshold of R2 in link13."
			::= { link13OBP 10 }


--  1.3.6.1.4.1.47477.10.21.13.3.29
		-- 1.3.6.1.4.1.47477.10.21.13.3.29
		link13_R3AlarmPower OBJECT-TYPE
			SYNTAX DisplayString
			MAX-ACCESS read-write
			STATUS current
			DESCRIPTION
				"get or set the power alarm threshold of R3 in link13."
			::= { link13OBP 29 }

		
--  1.3.6.1.4.1.47477.10.21.13.3.30
		-- 1.3.6.1.4.1.47477.10.21.13.3.30
		link13_R4AlarmPower OBJECT-TYPE
			SYNTAX DisplayString
			MAX-ACCESS read-write
			STATUS current
			DESCRIPTION
				"get or set the power alarm threshold of R4 in link13."
			::= { link13OBP 30 }

-- OBP4
--  1.3.6.1.4.1.47477.10.21.13.3.37
		-- 1.3.6.1.4.1.47477.10.21.13.3.37
		link13_1R1Power OBJECT-TYPE
			SYNTAX DisplayString
			MAX-ACCESS read-only
			STATUS current
			DESCRIPTION
				"get the power of 1R1 in link13."
			::= { link13OBP 37 }
			
--  1.3.6.1.4.1.47477.10.21.13.3.38
		-- 1.3.6.1.4.1.47477.10.21.13.3.38
		link13_1R2Power OBJECT-TYPE
			SYNTAX DisplayString
			MAX-ACCESS read-only
			STATUS current
			DESCRIPTION
				"get the power of 1R2 in link13."
			::= { link13OBP 38 }

--  1.3.6.1.4.1.47477.10.21.13.3.39
		-- 1.3.6.1.4.1.47477.10.21.13.3.39
		link13_1R3Power OBJECT-TYPE
			SYNTAX DisplayString
			MAX-ACCESS read-only
			STATUS current
			DESCRIPTION
				"get the power of 1R3 in link13."
			::= { link13OBP 39 }
			
--  1.3.6.1.4.1.47477.10.21.13.3.40
		-- 1.3.6.1.4.1.47477.10.21.13.3.40
		link13_1R4Power OBJECT-TYPE
			SYNTAX DisplayString
			MAX-ACCESS read-only
			STATUS current
			DESCRIPTION
				"get the power of 1R4 in link13."
			::= { link13OBP 40 }

--  1.3.6.1.4.1.47477.10.21.13.3.41
		-- 1.3.6.1.4.1.47477.10.21.13.3.41
		link13_2R1Power OBJECT-TYPE
			SYNTAX DisplayString
			MAX-ACCESS read-only
			STATUS current
			DESCRIPTION
				"get the power of 2R1 in link13."
			::= { link13OBP 41 }
			
--  1.3.6.1.4.1.47477.10.21.13.3.42
		-- 1.3.6.1.4.1.47477.10.21.13.3.42
		link13_2R2Power OBJECT-TYPE
			SYNTAX DisplayString
			MAX-ACCESS read-only
			STATUS current
			DESCRIPTION
				"get the power of 2R2 in link13."
			::= { link13OBP 42 }

--  1.3.6.1.4.1.47477.10.21.13.3.41
		-- 1.3.6.1.4.1.47477.10.21.13.3.43
		link13_2R3Power OBJECT-TYPE
			SYNTAX DisplayString
			MAX-ACCESS read-only
			STATUS current
			DESCRIPTION
				"get the power of 2R3 in link13."
			::= { link13OBP 43 }
			
--  1.3.6.1.4.1.47477.10.21.13.3.42
		-- 1.3.6.1.4.1.47477.10.21.13.3.44
		link13_2R4Power OBJECT-TYPE
			SYNTAX DisplayString
			MAX-ACCESS read-only
			STATUS current
			DESCRIPTION
				"get the power of 2R4 in link13."
			::= { link13OBP 44 }
			
--  1.3.6.1.4.1.47477.10.21.13.3.49
		-- 1.3.6.1.4.1.47477.10.21.13.3.49
		link13_1R1Wave OBJECT-TYPE
			SYNTAX INTEGER
				{
				w850nm(0),
				na(2)
				}
			MAX-ACCESS read-only
			STATUS current
			DESCRIPTION
				"get the wave length of 1R1 in link13."
			::= { link13OBP 49 }
		
--  1.3.6.1.4.1.47477.10.21.13.3.60
		-- 1.3.6.1.4.1.47477.10.21.13.3.60
		link13_1R2Wave OBJECT-TYPE
			SYNTAX INTEGER
				{
				w850nm(0),
				na(2)
				}
			MAX-ACCESS read-only
			STATUS current
			DESCRIPTION
				"get the wave length of 1R2 in link13."
			::= { link13OBP 60 }

--  1.3.6.1.4.1.47477.10.21.13.3.61
		-- 1.3.6.1.4.1.47477.10.21.13.3.61
		link13_1R3Wave OBJECT-TYPE
			SYNTAX INTEGER
				{
				w850nm(0),
				na(2)
				}
			MAX-ACCESS read-only
			STATUS current
			DESCRIPTION
				"get the wave length of 1R3 in link13."
			::= { link13OBP 61 }

		
--  1.3.6.1.4.1.47477.10.21.13.3.62
		-- 1.3.6.1.4.1.47477.10.21.13.3.62
		link13_1R4Wave OBJECT-TYPE
			SYNTAX INTEGER
				{
				w850nm(0),
				na(2)
				}
			MAX-ACCESS read-only
			STATUS current
			DESCRIPTION
				"get the wave length of 1R4 in link13."
			::= { link13OBP 62 }
	
--  1.3.6.1.4.1.47477.10.21.13.3.63
		-- 1.3.6.1.4.1.47477.10.21.13.3.63
		link13_2R1Wave OBJECT-TYPE
			SYNTAX INTEGER
				{
				w850nm(0),
				na(2)
				}
			MAX-ACCESS read-only
			STATUS current
			DESCRIPTION
				"get the wave length of 2R1 in link13."
			::= { link13OBP 63 }

		
--  1.3.6.1.4.1.47477.10.21.13.3.64
		-- 1.3.6.1.4.1.47477.10.21.13.3.64
		link13_2R2Wave OBJECT-TYPE
			SYNTAX INTEGER
				{
				w850nm(0),
				na(2)
				}
			MAX-ACCESS read-only
			STATUS current
			DESCRIPTION
				"get the wave length of 2R2 in link13."
			::= { link13OBP 64 }	
	
--  1.3.6.1.4.1.47477.10.21.13.3.65
		-- 1.3.6.1.4.1.47477.10.21.13.3.65
		link13_2R3Wave OBJECT-TYPE
			SYNTAX INTEGER
				{
				w850nm(0),
				na(2)
				}
			MAX-ACCESS read-only
			STATUS current
			DESCRIPTION
				"get the wave length of 2R3 in link13."
			::= { link13OBP 65 }

		
--  1.3.6.1.4.1.47477.10.21.13.3.66
		-- 1.3.6.1.4.1.47477.10.21.13.3.66
		link13_2R4Wave OBJECT-TYPE
			SYNTAX INTEGER
				{
				w850nm(0),
				na(2)
				}
			MAX-ACCESS read-only
			STATUS current
			DESCRIPTION
				"get the wave length of 2R4 in link13."
			::= { link13OBP 66 }	
			
--  1.3.6.1.4.1.47477.10.21.13.3.31
		-- 1.3.6.1.4.1.47477.10.21.13.3.31
		link13_1R1AlarmPower OBJECT-TYPE
			SYNTAX DisplayString
			MAX-ACCESS read-write
			STATUS current
			DESCRIPTION
				"get or set the power alarm threshold of 1R1 in link13."
			::= { link13OBP 31 }
			
--  1.3.6.1.4.1.47477.10.21.13.3.32
		-- 1.3.6.1.4.1.47477.10.21.13.3.32
		link13_1R2AlarmPower OBJECT-TYPE
			SYNTAX DisplayString
			MAX-ACCESS read-write
			STATUS current
			DESCRIPTION
				"get or set the power alarm threshold of 1R2 in link13."
			::= { link13OBP 32 }

--  1.3.6.1.4.1.47477.10.21.13.3.33
		-- 1.3.6.1.4.1.47477.10.21.13.3.33
		link13_1R3AlarmPower OBJECT-TYPE
			SYNTAX DisplayString
			MAX-ACCESS read-write
			STATUS current
			DESCRIPTION
				"get or set the power alarm threshold of 1R3 in link13."
			::= { link13OBP 33 }
			
--  1.3.6.1.4.1.47477.10.21.13.3.34
		-- 1.3.6.1.4.1.47477.10.21.13.3.34
		link13_1R4AlarmPower OBJECT-TYPE
			SYNTAX DisplayString
			MAX-ACCESS read-write
			STATUS current
			DESCRIPTION
				"get or set the power alarm threshold of 1R4 in link13."
			::= { link13OBP 34 }

--  1.3.6.1.4.1.47477.10.21.13.3.45
		-- 1.3.6.1.4.1.47477.10.21.13.3.45
		link13_2R1AlarmPower OBJECT-TYPE
			SYNTAX DisplayString
			MAX-ACCESS read-write
			STATUS current
			DESCRIPTION
				"get or set the power alarm threshold of 2R1 in link13."
			::= { link13OBP 45 }
			
--  1.3.6.1.4.1.47477.10.21.13.3.46
		-- 1.3.6.1.4.1.47477.10.21.13.3.46
		link13_2R2AlarmPower OBJECT-TYPE
			SYNTAX DisplayString
			MAX-ACCESS read-write
			STATUS current
			DESCRIPTION
				"get or set the power alarm threshold of 2R2 in link13."
			::= { link13OBP 46 }

--  1.3.6.1.4.1.47477.10.21.13.3.47
		-- 1.3.6.1.4.1.47477.10.21.13.3.47
		link13_2R3AlarmPower OBJECT-TYPE
			SYNTAX DisplayString
			MAX-ACCESS read-write
			STATUS current
			DESCRIPTION
				"get or set the power alarm threshold of 2R3 in link13."
			::= { link13OBP 47 }
			
--  1.3.6.1.4.1.47477.10.21.13.3.48
		-- 1.3.6.1.4.1.47477.10.21.13.3.48
		link13_2R4AlarmPower OBJECT-TYPE
			SYNTAX DisplayString
			MAX-ACCESS read-write
			STATUS current
			DESCRIPTION
				"get or set the power alarm threshold of 2R4 in link13."
			::= { link13OBP 48 }
			
--  1.3.6.1.4.1.47477.10.21.13.3.11
		-- 1.3.6.1.4.1.47477.10.21.13.3.11
		link13_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link13OBP 11 }
			
--  1.3.6.1.4.1.47477.10.21.13.3.67
		-- 1.3.6.1.4.1.47477.10.21.13.3.67
		link13_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link13OBP 67 }
			
--  1.3.6.1.4.1.47477.10.21.13.3.68
		-- 1.3.6.1.4.1.47477.10.21.13.3.68
		link13_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link13OBP 68 }
			
--  1.3.6.1.4.1.47477.10.21.13.3.12
		-- 1.3.6.1.4.1.47477.10.21.13.3.12
		link13_ReturnDelay OBJECT-TYPE
			--SYNTAX Integer32
			SYNTAX Integer32
			MAX-ACCESS read-write
			STATUS current
			DESCRIPTION
				"get or set how long link13 takes to return to automatic mode."
			::= { link13OBP 12 }
			
--  1.3.6.1.4.1.47477.10.21.13.3.13
		-- 1.3.6.1.4.1.47477.10.21.13.3.13
		link13_BackMode OBJECT-TYPE
			SYNTAX INTEGER
				{
				autoNoBack(0),
				autoBack(1)
				}
			MAX-ACCESS read-write
			STATUS current
			DESCRIPTION
				"get or set the back mode of link13."
			::= { link13OBP 13 }

		
--  1.3.6.1.4.1.47477.10.21.13.3.14
		-- 1.3.6.1.4.1.47477.10.21.13.3.14
		link13_BackDelay OBJECT-TYPE
			SYNTAX Integer32
			MAX-ACCESS read-write
			STATUS current
			DESCRIPTION
				"get or set the back delay."
			::= { link13OBP 14 }

--  1.3.6.1.4.1.47477.10.21.13.3.15
		-- 1.3.6.1.4.1.47477.10.21.13.3.15
		link13_ActiveHeartSwitch OBJECT-TYPE
			SYNTAX INTEGER
				{
				off(0),
				on(1)
				}
			MAX-ACCESS read-write
			STATUS current
			DESCRIPTION
				"get or set the switch status of active heartbeat."
			::= { link13OBP 15 }

		
--  1.3.6.1.4.1.47477.10.21.13.3.16
		-- 1.3.6.1.4.1.47477.10.21.13.3.16
		link13_ActiveSendInterval OBJECT-TYPE
			SYNTAX Integer32
			MAX-ACCESS read-write
			STATUS current
			DESCRIPTION
				"get or set the send interval of active heartbeat."
			::= { link13OBP 16 }		

--  1.3.6.1.4.1.47477.10.21.13.3.17
		-- 1.3.6.1.4.1.47477.10.21.13.3.17
		link13_ActiveTimeOut OBJECT-TYPE
			SYNTAX Integer32
			MAX-ACCESS read-write
			STATUS current
			DESCRIPTION
				"get or set how long the active heartbeat send timeout."
			::= { link13OBP 17 }

--  1.3.6.1.4.1.47477.10.21.13.3.18
		-- 1.3.6.1.4.1.47477.10.21.13.3.18
		link13_ActiveLossBypass OBJECT-TYPE
			SYNTAX Integer32
			MAX-ACCESS read-write
			STATUS current
			DESCRIPTION
				"get or set the bypass for active heartbeat packet loss."
			::= { link13OBP 18 }

--  1.3.6.1.4.1.47477.10.21.13.3.19
		-- 1.3.6.1.4.1.47477.10.21.13.3.19
		link13_PingIpAddress OBJECT-TYPE
			SYNTAX IpAddress
			MAX-ACCESS read-write
			STATUS current
			DESCRIPTION
				"get or set the ping ip address of link13."
			::= { link13OBP 19 }

--  1.3.6.1.4.1.47477.10.21.13.3.20
		-- 1.3.6.1.4.1.47477.10.21.13.3.20
		link13_PassiveHeartSwitch OBJECT-TYPE
			SYNTAX INTEGER
				{
				off(0),
				on(1)
				}
			MAX-ACCESS read-write
			STATUS current
			DESCRIPTION
				"get or set the switch status of passive heartbeat."
			::= { link13OBP 20 }
	

--  1.3.6.1.4.1.47477.10.21.13.3.21
		-- 1.3.6.1.4.1.47477.10.21.13.3.21
		link13_PassiveTimeOut OBJECT-TYPE
			SYNTAX Integer32
			MAX-ACCESS read-write
			STATUS current
			DESCRIPTION
				"get or set how long the passive heartbeat send timeout."
			::= { link13OBP 21 }

--  1.3.6.1.4.1.47477.10.21.13.3.22
		-- 1.3.6.1.4.1.47477.10.21.13.3.22
		link13_PassiveLossBypass OBJECT-TYPE
			SYNTAX Integer32
			MAX-ACCESS read-write
			STATUS current
			DESCRIPTION
				"get or set the bypass for passive heartbeat packet loss."
			::= { link13OBP 22 }

--  1.3.6.1.4.1.47477.10.21.13.3.23
		-- 1.3.6.1.4.1.47477.10.21.13.3.23
		link13_SwitchProtect OBJECT-TYPE
			SYNTAX INTEGER
				{
				off(0),
				on(1)
				}
			MAX-ACCESS read-write
			STATUS current
			DESCRIPTION
				"get or set the switch protection status of link13."
			::= { link13OBP 23 }
			
--  1.3.6.1.4.1.47477.10.21.13.3.24
		-- 1.3.6.1.4.1.47477.10.21.13.3.24
		link13_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link13OBP 24 }		

--  1.3.6.1.4.1.47477.10.21.13.3.25
		-- 1.3.6.1.4.1.47477.10.21.13.3.25
		link13_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link13OBP 25 }	

--  1.3.6.1.4.1.47477.10.21.13.3.26
		-- 1.3.6.1.4.1.47477.10.21.13.3.26
		link13_PowerAlarmStatus OBJECT-TYPE
			SYNTAX INTEGER
				{
				off(0),
				alarm(1),
				normal(2),
				na(3)
				}
			MAX-ACCESS read-only
			STATUS current
			DESCRIPTION
				"get whether a power alarm is generated."
			::= { link13OBP 26 }	


-- 1.3.6.1.4.1.47477.10.21.13.3.50.1
	link13_WorkModeChange 	OBJECT-TYPE    
    SYNTAX INTEGER	{
				manualMode(0),
				autoMode(1)
		}
	MAX-ACCESS read-only
	STATUS current
    DESCRIPTION
        "The Link mode Changed."
    ::= {link13OBPTrap 1}

-- 1.3.6.1.4.1.47477.10.21.13.3.50.2
	link13_StateChange 	OBJECT-TYPE    
    SYNTAX INTEGER	{
				bypass(0),
				primary(1)
		}
	MAX-ACCESS read-only
	STATUS current
    DESCRIPTION
        "The Link State(Channel) Changed."
    ::= {link13OBPTrap 2}

-- 1.3.6.1.4.1.47477.10.21.13.3.50.3
	link13_R1WaveSet 	OBJECT-TYPE    
    SYNTAX INTEGER	{
				w1310nm(0),
				w1550nm(1)
		}
	MAX-ACCESS read-only
	STATUS current
    DESCRIPTION
        "Set The link13 R1 Wave."
    ::= {link13OBPTrap 3}

-- 1.3.6.1.4.1.47477.10.21.13.3.50.4
	link13_R2WaveSet 	OBJECT-TYPE    
    SYNTAX INTEGER	{
				w1310nm(0),
				w1550nm(1)
		}
	MAX-ACCESS read-only
	STATUS current
    DESCRIPTION
        "Set The link13 R2 Wave."
    ::= {link13OBPTrap 4}			

-- 1.3.6.1.4.1.47477.10.21.13.3.50.5
	link13_R3WaveSet 	OBJECT-TYPE    
    SYNTAX INTEGER	{
				w1310nm(0),
				w1550nm(1)
		}
	MAX-ACCESS read-only
	STATUS current
    DESCRIPTION
        "Set The link13 R3 Wave."
    ::= {link13OBPTrap 5}

-- 1.3.6.1.4.1.47477.10.21.13.3.50.6
	link13_R4WaveSet 	OBJECT-TYPE    
    SYNTAX INTEGER	{
				w1310nm(0),
				w1550nm(1)
		}
	MAX-ACCESS read-only
	STATUS current
    DESCRIPTION
        "Set The link13 R4 Wave."
    ::= {link13OBPTrap 6}	
	
-- 1.3.6.1.4.1.47477.10.21.13.3.50.7
	link13_R1AlarmSet 	OBJECT-TYPE    
    SYNTAX DisplayString
	MAX-ACCESS read-only
	STATUS current
    DESCRIPTION
        "Set The link13 R1 Alarm Threshold."
    ::= {link13OBPTrap 7}

-- 1.3.6.1.4.1.47477.10.21.13.3.50.8
	link13_R2AlarmSet 	OBJECT-TYPE    
    SYNTAX DisplayString
	MAX-ACCESS read-only
	STATUS current
    DESCRIPTION
        "Set The link13 R2 Alarm Threshold."
    ::= {link13OBPTrap 8}
	
-- 1.3.6.1.4.1.47477.10.21.13.3.50.9
	link13_R3AlarmSet 	OBJECT-TYPE    
    SYNTAX DisplayString
	MAX-ACCESS read-only
	STATUS current
    DESCRIPTION
        "Set The link13 R3 Alarm Threshold."
    ::= {link13OBPTrap 9}

-- 1.3.6.1.4.1.47477.10.21.13.3.50.10
	link13_R4AlarmSet 	OBJECT-TYPE    
    SYNTAX DisplayString
	MAX-ACCESS read-only
	STATUS current
    DESCRIPTION
        "Set The link13 R4 Alarm Threshold."
    ::= {link13OBPTrap 10}	
	
	
-- 1.3.6.1.4.1.47477.10.21.13.3.50.11
	link13_1R1AlarmSet 	OBJECT-TYPE    
    SYNTAX DisplayString
	MAX-ACCESS read-only
	STATUS current
    DESCRIPTION
        "Set The link13 1R1 Alarm Threshold."
    ::= {link13OBPTrap 11}

-- 1.3.6.1.4.1.47477.10.21.13.3.50.12
	link13_2R1AlarmSet 	OBJECT-TYPE    
    SYNTAX DisplayString
	MAX-ACCESS read-only
	STATUS current
    DESCRIPTION
        "Set The link13 2R1 Alarm Threshold."
    ::= {link13OBPTrap 12}
	
-- 1.3.6.1.4.1.47477.10.21.13.3.50.13
	link13_1R2AlarmSet 	OBJECT-TYPE    
    SYNTAX DisplayString
	MAX-ACCESS read-only
	STATUS current
    DESCRIPTION
        "Set The link13 1R2 Alarm Threshold."
    ::= {link13OBPTrap 13}

-- 1.3.6.1.4.1.47477.10.21.13.3.50.14
	link13_2R2AlarmSet 	OBJECT-TYPE    
    SYNTAX DisplayString
	MAX-ACCESS read-only
	STATUS current
    DESCRIPTION
        "Set The link13 2R2 Alarm Threshold."
    ::= {link13OBPTrap 14}
	
-- 1.3.6.1.4.1.47477.10.21.13.3.50.15
	link13_1R3AlarmSet 	OBJECT-TYPE    
    SYNTAX DisplayString
	MAX-ACCESS read-only
	STATUS current
    DESCRIPTION
        "Set The link13 1R3 Alarm Threshold."
    ::= {link13OBPTrap 15}

-- 1.3.6.1.4.1.47477.10.21.13.3.50.16
	link13_2R3AlarmSet 	OBJECT-TYPE    
    SYNTAX DisplayString
	MAX-ACCESS read-only
	STATUS current
    DESCRIPTION
        "Set The link13 2R3 Alarm Threshold."
    ::= {link13OBPTrap 16}
	
-- 1.3.6.1.4.1.47477.10.21.13.3.50.17
	link13_1R4AlarmSet 	OBJECT-TYPE    
    SYNTAX DisplayString
	MAX-ACCESS read-only
	STATUS current
    DESCRIPTION
        "Set The link13 1R4 Alarm Threshold."
    ::= {link13OBPTrap 17}

-- 1.3.6.1.4.1.47477.10.21.13.3.50.18
	link13_2R4AlarmSet 	OBJECT-TYPE    
    SYNTAX DisplayString
	MAX-ACCESS read-only
	STATUS current
    DESCRIPTION
        "Set The link13 2R4 Alarm Threshold."
    ::= {link13OBPTrap 18}
	
-- 1.3.6.1.4.1.47477.10.21.13.3.50.19
	link13_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link13 PowerAlarmBypass2 Changed."
    ::= {link13OBPTrap 19}
	
-- 1.3.6.1.4.1.47477.10.21.13.3.50.20
	link13_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link13 PowerAlarmBypass4 Changed."
    ::= {link13OBPTrap 20}	
	
-- 1.3.6.1.4.1.47477.10.21.13.3.50.21
	link13_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link13 PowerAlarmBypass8 Changed."
    ::= {link13OBPTrap 21}
	
-- 1.3.6.1.4.1.47477.10.21.13.3.50.22
	link13_powerAlarmR1 	OBJECT-TYPE    
    SYNTAX DisplayString
	MAX-ACCESS read-only
	STATUS current
    DESCRIPTION
        "Set The link13 R1 Power Status Alarm."
    ::= {link13OBPTrap 22}
	
-- 1.3.6.1.4.1.47477.10.21.13.3.50.23
	link13_powerAlarmR2 	OBJECT-TYPE    
    SYNTAX DisplayString
	MAX-ACCESS read-only
	STATUS current
    DESCRIPTION
        "Set The link13 R2 Power Status Alarm."
    ::= {link13OBPTrap 23}
	
-- 1.3.6.1.4.1.47477.10.21.13.3.50.24
	link13_powerAlarmR3 	OBJECT-TYPE    
    SYNTAX DisplayString
	MAX-ACCESS read-only
	STATUS current
    DESCRIPTION
        "Set The link13 R3 Power Status Alarm."
    ::= {link13OBPTrap 24}
	
-- 1.3.6.1.4.1.47477.10.21.13.3.50.25
	link13_powerAlarmR4 	OBJECT-TYPE    
    SYNTAX DisplayString
	MAX-ACCESS read-only
	STATUS current
    DESCRIPTION
        "Set The link13 R4 Power Status Alarm."
    ::= {link13OBPTrap 25}
	
	
-- 1.3.6.1.4.1.47477.10.21.13.3.50.26
	link13_powerAlarm1R1 	OBJECT-TYPE    
    SYNTAX DisplayString
	MAX-ACCESS read-only
	STATUS current
    DESCRIPTION
        "Set The link13 1R1 Power Status Alarm."
    ::= {link13OBPTrap 26}
	
-- 1.3.6.1.4.1.47477.10.21.13.3.50.27
	link13_powerAlarm2R1 	OBJECT-TYPE    
    SYNTAX DisplayString
	MAX-ACCESS read-only
	STATUS current
    DESCRIPTION
        "Set The link13 2R1 Power Status Alarm."
    ::= {link13OBPTrap 27}
	
-- 1.3.6.1.4.1.47477.10.21.13.3.50.28
	link13_powerAlarm1R2 	OBJECT-TYPE    
    SYNTAX DisplayString
	MAX-ACCESS read-only
	STATUS current
    DESCRIPTION
        "Set The link13 1R2 Power Status Alarm."
    ::= {link13OBPTrap 28}
	
-- 1.3.6.1.4.1.47477.10.21.13.3.50.29
	link13_powerAlarm2R2 	OBJECT-TYPE    
    SYNTAX DisplayString
	MAX-ACCESS read-only
	STATUS current
    DESCRIPTION
        "Set The link13 2R2 Power Status Alarm."
    ::= {link13OBPTrap 29}
	
-- 1.3.6.1.4.1.47477.10.21.13.3.50.30
	link13_powerAlarm1R3 	OBJECT-TYPE    
    SYNTAX DisplayString
	MAX-ACCESS read-only
	STATUS current
    DESCRIPTION
        "Set The link13 1R3 Power Status Alarm."
    ::= {link13OBPTrap 30}
	
-- 1.3.6.1.4.1.47477.10.21.13.3.50.31
	link13_powerAlarm2R3 	OBJECT-TYPE    
    SYNTAX DisplayString
	MAX-ACCESS read-only
	STATUS current
    DESCRIPTION
        "Set The link13 2R1 Power Status Alarm."
    ::= {link13OBPTrap 31}
	
-- 1.3.6.1.4.1.47477.10.21.13.3.50.32
	link13_powerAlarm1R4 	OBJECT-TYPE    
    SYNTAX DisplayString
	MAX-ACCESS read-only
	STATUS current
    DESCRIPTION
        "Set The link13 1R4 Power Status Alarm."
    ::= {link13OBPTrap 32}
	
-- 1.3.6.1.4.1.47477.10.21.13.3.50.33
	link13_powerAlarm2R4 	OBJECT-TYPE    
    SYNTAX DisplayString
	MAX-ACCESS read-only
	STATUS current
    DESCRIPTION
        "Set The link13 2R4 Power Status Alarm."
    ::= {link13OBPTrap 33}
	
--  1.3.6.1.4.1.47477.10.21.14.3.1
		-- 1.3.6.1.4.1.47477.10.21.14.3.1
		link14_State OBJECT-TYPE
			SYNTAX INTEGER
				{
				off(0),
				on(1)
				}
			MAX-ACCESS read-only
			STATUS current
			DESCRIPTION
				"get the information about whether link14 is working."
			::= { link14OBP 1 }

		
--  1.3.6.1.4.1.47477.10.21.14.3.2
		-- 1.3.6.1.4.1.47477.10.21.14.3.2
		link14_DeviceType OBJECT-TYPE
			SYNTAX DisplayString
			MAX-ACCESS read-only
			STATUS current
			DESCRIPTION
				"get the type of card in link14."
			::= { link14OBP 2 }

			
--  1.3.6.1.4.1.47477.10.21.14.3.3
		-- 1.3.6.1.4.1.47477.10.21.14.3.3
		link14_WorkMode OBJECT-TYPE
			SYNTAX INTEGER
				{
				manualMode(0),
				autoMode(1)
				}
			MAX-ACCESS read-write
			STATUS current
			DESCRIPTION
				"get or set link14's work mode."
			::= { link14OBP 3 }

		
--  1.3.6.1.4.1.47477.10.21.14.3.4
		-- 1.3.6.1.4.1.47477.10.21.14.3.4
		link14_Channel OBJECT-TYPE
			SYNTAX INTEGER
				{
				bypass(0),
				primary(1)
				}
			MAX-ACCESS read-write
			STATUS current
			DESCRIPTION
				"get or set the channel in which link14 works."
			::= { link14OBP 4 }


--  1.3.6.1.4.1.47477.10.21.14.3.5
		-- 1.3.6.1.4.1.47477.10.21.14.3.5
		link14_R1Power OBJECT-TYPE
			SYNTAX DisplayString
			MAX-ACCESS read-only
			STATUS current
			DESCRIPTION
				"get the power of R1 in link14."
			::= { link14OBP 5 }

		
--  1.3.6.1.4.1.47477.10.21.14.3.6
		-- 1.3.6.1.4.1.47477.10.21.14.3.6
		link14_R2Power OBJECT-TYPE
			SYNTAX DisplayString
			MAX-ACCESS read-only
			STATUS current
			DESCRIPTION
				"get the power of R2 in link14."
			::= { link14OBP 6 }
			
--  1.3.6.1.4.1.47477.10.21.14.3.35
		-- 1.3.6.1.4.1.47477.10.21.14.3.35
		link14_R3Power OBJECT-TYPE
			SYNTAX DisplayString
			MAX-ACCESS read-only
			STATUS current
			DESCRIPTION
				"get the power of R3 in link14."
			::= { link14OBP 35 }
			
--  1.3.6.1.4.1.47477.10.21.14.3.36
		-- 1.3.6.1.4.1.47477.10.21.14.3.36
		link14_R4Power OBJECT-TYPE
			SYNTAX DisplayString
			MAX-ACCESS read-only
			STATUS current
			DESCRIPTION
				"get the power of R4 in link14."
			::= { link14OBP 36 }		
		
--  1.3.6.1.4.1.47477.10.21.14.3.7
		-- 1.3.6.1.4.1.47477.10.21.14.3.7
		link14_R1Wave OBJECT-TYPE
			SYNTAX INTEGER
				{
				w1310nm(0),
				w1550nm(1),
				na(2)
				}
			MAX-ACCESS read-write
			STATUS current
			DESCRIPTION
				"get or set the wave length of R1 in link14."
			::= { link14OBP 7 }

		
--  1.3.6.1.4.1.47477.10.21.14.3.8
		-- 1.3.6.1.4.1.47477.10.21.14.3.8
		link14_R2Wave OBJECT-TYPE
			SYNTAX INTEGER
				{
				w1310nm(0),
				w1550nm(1),
				na(2)
				}
			MAX-ACCESS read-write
			STATUS current
			DESCRIPTION
				"get or set the wave length of R2 in link14."
			::= { link14OBP 8 }


--  1.3.6.1.4.1.47477.10.21.14.3.27
		-- 1.3.6.1.4.1.47477.10.21.14.3.27
		link14_R3Wave OBJECT-TYPE
			SYNTAX INTEGER
				{
				w1310nm(0),
				w1550nm(1),
				na(2)
				}
			MAX-ACCESS read-write
			STATUS current
			DESCRIPTION
				"get or set the wave length of R3 in link14."
			::= { link14OBP 27 }

		
--  1.3.6.1.4.1.47477.10.21.14.3.28
		-- 1.3.6.1.4.1.47477.10.21.14.3.28
		link14_R4Wave OBJECT-TYPE
			SYNTAX INTEGER
				{
				w1310nm(0),
				w1550nm(1),
				na(2)
				}
			MAX-ACCESS read-write
			STATUS current
			DESCRIPTION
				"get or set the wave length of R4 in link14."
			::= { link14OBP 28 }
			
--  1.3.6.1.4.1.47477.10.21.14.3.9
		-- 1.3.6.1.4.1.47477.10.21.14.3.9
		link14_R1AlarmPower OBJECT-TYPE
			SYNTAX DisplayString
			MAX-ACCESS read-write
			STATUS current
			DESCRIPTION
				"get or set the power alarm threshold of R1 in link14."
			::= { link14OBP 9 }

		
--  1.3.6.1.4.1.47477.10.21.14.3.10
		-- 1.3.6.1.4.1.47477.10.21.14.3.10
		link14_R2AlarmPower OBJECT-TYPE
			SYNTAX DisplayString
			MAX-ACCESS read-write
			STATUS current
			DESCRIPTION
				"get or set the power alarm threshold of R2 in link14."
			::= { link14OBP 10 }


--  1.3.6.1.4.1.47477.10.21.14.3.29
		-- 1.3.6.1.4.1.47477.10.21.14.3.29
		link14_R3AlarmPower OBJECT-TYPE
			SYNTAX DisplayString
			MAX-ACCESS read-write
			STATUS current
			DESCRIPTION
				"get or set the power alarm threshold of R3 in link14."
			::= { link14OBP 29 }

		
--  1.3.6.1.4.1.47477.10.21.14.3.30
		-- 1.3.6.1.4.1.47477.10.21.14.3.30
		link14_R4AlarmPower OBJECT-TYPE
			SYNTAX DisplayString
			MAX-ACCESS read-write
			STATUS current
			DESCRIPTION
				"get or set the power alarm threshold of R4 in link14."
			::= { link14OBP 30 }

-- OBP4
--  1.3.6.1.4.1.47477.10.21.14.3.37
		-- 1.3.6.1.4.1.47477.10.21.14.3.37
		link14_1R1Power OBJECT-TYPE
			SYNTAX DisplayString
			MAX-ACCESS read-only
			STATUS current
			DESCRIPTION
				"get the power of 1R1 in link14."
			::= { link14OBP 37 }
			
--  1.3.6.1.4.1.47477.10.21.14.3.38
		-- 1.3.6.1.4.1.47477.10.21.14.3.38
		link14_1R2Power OBJECT-TYPE
			SYNTAX DisplayString
			MAX-ACCESS read-only
			STATUS current
			DESCRIPTION
				"get the power of 1R2 in link14."
			::= { link14OBP 38 }

--  1.3.6.1.4.1.47477.10.21.14.3.39
		-- 1.3.6.1.4.1.47477.10.21.14.3.39
		link14_1R3Power OBJECT-TYPE
			SYNTAX DisplayString
			MAX-ACCESS read-only
			STATUS current
			DESCRIPTION
				"get the power of 1R3 in link14."
			::= { link14OBP 39 }
			
--  1.3.6.1.4.1.47477.10.21.14.3.40
		-- 1.3.6.1.4.1.47477.10.21.14.3.40
		link14_1R4Power OBJECT-TYPE
			SYNTAX DisplayString
			MAX-ACCESS read-only
			STATUS current
			DESCRIPTION
				"get the power of 1R4 in link14."
			::= { link14OBP 40 }

--  1.3.6.1.4.1.47477.10.21.14.3.41
		-- 1.3.6.1.4.1.47477.10.21.14.3.41
		link14_2R1Power OBJECT-TYPE
			SYNTAX DisplayString
			MAX-ACCESS read-only
			STATUS current
			DESCRIPTION
				"get the power of 2R1 in link14."
			::= { link14OBP 41 }
			
--  1.3.6.1.4.1.47477.10.21.14.3.42
		-- 1.3.6.1.4.1.47477.10.21.14.3.42
		link14_2R2Power OBJECT-TYPE
			SYNTAX DisplayString
			MAX-ACCESS read-only
			STATUS current
			DESCRIPTION
				"get the power of 2R2 in link14."
			::= { link14OBP 42 }

--  1.3.6.1.4.1.47477.10.21.14.3.41
		-- 1.3.6.1.4.1.47477.10.21.14.3.43
		link14_2R3Power OBJECT-TYPE
			SYNTAX DisplayString
			MAX-ACCESS read-only
			STATUS current
			DESCRIPTION
				"get the power of 2R3 in link14."
			::= { link14OBP 43 }
			
--  1.3.6.1.4.1.47477.10.21.14.3.42
		-- 1.3.6.1.4.1.47477.10.21.14.3.44
		link14_2R4Power OBJECT-TYPE
			SYNTAX DisplayString
			MAX-ACCESS read-only
			STATUS current
			DESCRIPTION
				"get the power of 2R4 in link14."
			::= { link14OBP 44 }
			
--  1.3.6.1.4.1.47477.10.21.14.3.49
		-- 1.3.6.1.4.1.47477.10.21.14.3.49
		link14_1R1Wave OBJECT-TYPE
			SYNTAX INTEGER
				{
				w850nm(0),
				na(2)
				}
			MAX-ACCESS read-only
			STATUS current
			DESCRIPTION
				"get the wave length of 1R1 in link14."
			::= { link14OBP 49 }
		
--  1.3.6.1.4.1.47477.10.21.14.3.60
		-- 1.3.6.1.4.1.47477.10.21.14.3.60
		link14_1R2Wave OBJECT-TYPE
			SYNTAX INTEGER
				{
				w850nm(0),
				na(2)
				}
			MAX-ACCESS read-only
			STATUS current
			DESCRIPTION
				"get the wave length of 1R2 in link14."
			::= { link14OBP 60 }

--  1.3.6.1.4.1.47477.10.21.14.3.61
		-- 1.3.6.1.4.1.47477.10.21.14.3.61
		link14_1R3Wave OBJECT-TYPE
			SYNTAX INTEGER
				{
				w850nm(0),
				na(2)
				}
			MAX-ACCESS read-only
			STATUS current
			DESCRIPTION
				"get the wave length of 1R3 in link14."
			::= { link14OBP 61 }

		
--  1.3.6.1.4.1.47477.10.21.14.3.62
		-- 1.3.6.1.4.1.47477.10.21.14.3.62
		link14_1R4Wave OBJECT-TYPE
			SYNTAX INTEGER
				{
				w850nm(0),
				na(2)
				}
			MAX-ACCESS read-only
			STATUS current
			DESCRIPTION
				"get the wave length of 1R4 in link14."
			::= { link14OBP 62 }
	
--  1.3.6.1.4.1.47477.10.21.14.3.63
		-- 1.3.6.1.4.1.47477.10.21.14.3.63
		link14_2R1Wave OBJECT-TYPE
			SYNTAX INTEGER
				{
				w850nm(0),
				na(2)
				}
			MAX-ACCESS read-only
			STATUS current
			DESCRIPTION
				"get the wave length of 2R1 in link14."
			::= { link14OBP 63 }

		
--  1.3.6.1.4.1.47477.10.21.14.3.64
		-- 1.3.6.1.4.1.47477.10.21.14.3.64
		link14_2R2Wave OBJECT-TYPE
			SYNTAX INTEGER
				{
				w850nm(0),
				na(2)
				}
			MAX-ACCESS read-only
			STATUS current
			DESCRIPTION
				"get the wave length of 2R2 in link14."
			::= { link14OBP 64 }	
	
--  1.3.6.1.4.1.47477.10.21.14.3.65
		-- 1.3.6.1.4.1.47477.10.21.14.3.65
		link14_2R3Wave OBJECT-TYPE
			SYNTAX INTEGER
				{
				w850nm(0),
				na(2)
				}
			MAX-ACCESS read-only
			STATUS current
			DESCRIPTION
				"get the wave length of 2R3 in link14."
			::= { link14OBP 65 }

		
--  1.3.6.1.4.1.47477.10.21.14.3.66
		-- 1.3.6.1.4.1.47477.10.21.14.3.66
		link14_2R4Wave OBJECT-TYPE
			SYNTAX INTEGER
				{
				w850nm(0),
				na(2)
				}
			MAX-ACCESS read-only
			STATUS current
			DESCRIPTION
				"get the wave length of 2R4 in link14."
			::= { link14OBP 66 }	
			
--  1.3.6.1.4.1.47477.10.21.14.3.31
		-- 1.3.6.1.4.1.47477.10.21.14.3.31
		link14_1R1AlarmPower OBJECT-TYPE
			SYNTAX DisplayString
			MAX-ACCESS read-write
			STATUS current
			DESCRIPTION
				"get or set the power alarm threshold of 1R1 in link14."
			::= { link14OBP 31 }
			
--  1.3.6.1.4.1.47477.10.21.14.3.32
		-- 1.3.6.1.4.1.47477.10.21.14.3.32
		link14_1R2AlarmPower OBJECT-TYPE
			SYNTAX DisplayString
			MAX-ACCESS read-write
			STATUS current
			DESCRIPTION
				"get or set the power alarm threshold of 1R2 in link14."
			::= { link14OBP 32 }

--  1.3.6.1.4.1.47477.10.21.14.3.33
		-- 1.3.6.1.4.1.47477.10.21.14.3.33
		link14_1R3AlarmPower OBJECT-TYPE
			SYNTAX DisplayString
			MAX-ACCESS read-write
			STATUS current
			DESCRIPTION
				"get or set the power alarm threshold of 1R3 in link14."
			::= { link14OBP 33 }
			
--  1.3.6.1.4.1.47477.10.21.14.3.34
		-- 1.3.6.1.4.1.47477.10.21.14.3.34
		link14_1R4AlarmPower OBJECT-TYPE
			SYNTAX DisplayString
			MAX-ACCESS read-write
			STATUS current
			DESCRIPTION
				"get or set the power alarm threshold of 1R4 in link14."
			::= { link14OBP 34 }

--  1.3.6.1.4.1.47477.10.21.14.3.45
		-- 1.3.6.1.4.1.47477.10.21.14.3.45
		link14_2R1AlarmPower OBJECT-TYPE
			SYNTAX DisplayString
			MAX-ACCESS read-write
			STATUS current
			DESCRIPTION
				"get or set the power alarm threshold of 2R1 in link14."
			::= { link14OBP 45 }
			
--  1.3.6.1.4.1.47477.10.21.14.3.46
		-- 1.3.6.1.4.1.47477.10.21.14.3.46
		link14_2R2AlarmPower OBJECT-TYPE
			SYNTAX DisplayString
			MAX-ACCESS read-write
			STATUS current
			DESCRIPTION
				"get or set the power alarm threshold of 2R2 in link14."
			::= { link14OBP 46 }

--  1.3.6.1.4.1.47477.10.21.14.3.47
		-- 1.3.6.1.4.1.47477.10.21.14.3.47
		link14_2R3AlarmPower OBJECT-TYPE
			SYNTAX DisplayString
			MAX-ACCESS read-write
			STATUS current
			DESCRIPTION
				"get or set the power alarm threshold of 2R3 in link14."
			::= { link14OBP 47 }
			
--  1.3.6.1.4.1.47477.10.21.14.3.48
		-- 1.3.6.1.4.1.47477.10.21.14.3.48
		link14_2R4AlarmPower OBJECT-TYPE
			SYNTAX DisplayString
			MAX-ACCESS read-write
			STATUS current
			DESCRIPTION
				"get or set the power alarm threshold of 2R4 in link14."
			::= { link14OBP 48 }
			
--  1.3.6.1.4.1.47477.10.21.14.3.11
		-- 1.3.6.1.4.1.47477.10.21.14.3.11
		link14_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link14OBP 11 }
			
--  1.3.6.1.4.1.47477.10.21.14.3.67
		-- 1.3.6.1.4.1.47477.10.21.14.3.67
		link14_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link14OBP 67 }
			
--  1.3.6.1.4.1.47477.10.21.14.3.68
		-- 1.3.6.1.4.1.47477.10.21.14.3.68
		link14_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link14OBP 68 }
			
--  1.3.6.1.4.1.47477.10.21.14.3.12
		-- 1.3.6.1.4.1.47477.10.21.14.3.12
		link14_ReturnDelay OBJECT-TYPE
			--SYNTAX Integer32
			SYNTAX Integer32
			MAX-ACCESS read-write
			STATUS current
			DESCRIPTION
				"get or set how long link14 takes to return to automatic mode."
			::= { link14OBP 12 }
			
--  1.3.6.1.4.1.47477.10.21.14.3.13
		-- 1.3.6.1.4.1.47477.10.21.14.3.13
		link14_BackMode OBJECT-TYPE
			SYNTAX INTEGER
				{
				autoNoBack(0),
				autoBack(1)
				}
			MAX-ACCESS read-write
			STATUS current
			DESCRIPTION
				"get or set the back mode of link14."
			::= { link14OBP 13 }

		
--  1.3.6.1.4.1.47477.10.21.14.3.14
		-- 1.3.6.1.4.1.47477.10.21.14.3.14
		link14_BackDelay OBJECT-TYPE
			SYNTAX Integer32
			MAX-ACCESS read-write
			STATUS current
			DESCRIPTION
				"get or set the back delay."
			::= { link14OBP 14 }

--  1.3.6.1.4.1.47477.10.21.14.3.15
		-- 1.3.6.1.4.1.47477.10.21.14.3.15
		link14_ActiveHeartSwitch OBJECT-TYPE
			SYNTAX INTEGER
				{
				off(0),
				on(1)
				}
			MAX-ACCESS read-write
			STATUS current
			DESCRIPTION
				"get or set the switch status of active heartbeat."
			::= { link14OBP 15 }

		
--  1.3.6.1.4.1.47477.10.21.14.3.16
		-- 1.3.6.1.4.1.47477.10.21.14.3.16
		link14_ActiveSendInterval OBJECT-TYPE
			SYNTAX Integer32
			MAX-ACCESS read-write
			STATUS current
			DESCRIPTION
				"get or set the send interval of active heartbeat."
			::= { link14OBP 16 }		

--  1.3.6.1.4.1.47477.10.21.14.3.17
		-- 1.3.6.1.4.1.47477.10.21.14.3.17
		link14_ActiveTimeOut OBJECT-TYPE
			SYNTAX Integer32
			MAX-ACCESS read-write
			STATUS current
			DESCRIPTION
				"get or set how long the active heartbeat send timeout."
			::= { link14OBP 17 }

--  1.3.6.1.4.1.47477.10.21.14.3.18
		-- 1.3.6.1.4.1.47477.10.21.14.3.18
		link14_ActiveLossBypass OBJECT-TYPE
			SYNTAX Integer32
			MAX-ACCESS read-write
			STATUS current
			DESCRIPTION
				"get or set the bypass for active heartbeat packet loss."
			::= { link14OBP 18 }

--  1.3.6.1.4.1.47477.10.21.14.3.19
		-- 1.3.6.1.4.1.47477.10.21.14.3.19
		link14_PingIpAddress OBJECT-TYPE
			SYNTAX IpAddress
			MAX-ACCESS read-write
			STATUS current
			DESCRIPTION
				"get or set the ping ip address of link14."
			::= { link14OBP 19 }

--  1.3.6.1.4.1.47477.10.21.14.3.20
		-- 1.3.6.1.4.1.47477.10.21.14.3.20
		link14_PassiveHeartSwitch OBJECT-TYPE
			SYNTAX INTEGER
				{
				off(0),
				on(1)
				}
			MAX-ACCESS read-write
			STATUS current
			DESCRIPTION
				"get or set the switch status of passive heartbeat."
			::= { link14OBP 20 }
	

--  1.3.6.1.4.1.47477.10.21.14.3.21
		-- 1.3.6.1.4.1.47477.10.21.14.3.21
		link14_PassiveTimeOut OBJECT-TYPE
			SYNTAX Integer32
			MAX-ACCESS read-write
			STATUS current
			DESCRIPTION
				"get or set how long the passive heartbeat send timeout."
			::= { link14OBP 21 }

--  1.3.6.1.4.1.47477.10.21.14.3.22
		-- 1.3.6.1.4.1.47477.10.21.14.3.22
		link14_PassiveLossBypass OBJECT-TYPE
			SYNTAX Integer32
			MAX-ACCESS read-write
			STATUS current
			DESCRIPTION
				"get or set the bypass for passive heartbeat packet loss."
			::= { link14OBP 22 }

--  1.3.6.1.4.1.47477.10.21.14.3.23
		-- 1.3.6.1.4.1.47477.10.21.14.3.23
		link14_SwitchProtect OBJECT-TYPE
			SYNTAX INTEGER
				{
				off(0),
				on(1)
				}
			MAX-ACCESS read-write
			STATUS current
			DESCRIPTION
				"get or set the switch protection status of link14."
			::= { link14OBP 23 }
			
--  1.3.6.1.4.1.47477.10.21.14.3.24
		-- 1.3.6.1.4.1.47477.10.21.14.3.24
		link14_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link14OBP 24 }		

--  1.3.6.1.4.1.47477.10.21.14.3.25
		-- 1.3.6.1.4.1.47477.10.21.14.3.25
		link14_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link14OBP 25 }	

--  1.3.6.1.4.1.47477.10.21.14.3.26
		-- 1.3.6.1.4.1.47477.10.21.14.3.26
		link14_PowerAlarmStatus OBJECT-TYPE
			SYNTAX INTEGER
				{
				off(0),
				alarm(1),
				normal(2),
				na(3)
				}
			MAX-ACCESS read-only
			STATUS current
			DESCRIPTION
				"get whether a power alarm is generated."
			::= { link14OBP 26 }	


-- 1.3.6.1.4.1.47477.10.21.14.3.50.1
	link14_WorkModeChange 	OBJECT-TYPE    
    SYNTAX INTEGER	{
				manualMode(0),
				autoMode(1)
		}
	MAX-ACCESS read-only
	STATUS current
    DESCRIPTION
        "The Link mode Changed."
    ::= {link14OBPTrap 1}

-- 1.3.6.1.4.1.47477.10.21.14.3.50.2
	link14_StateChange 	OBJECT-TYPE    
    SYNTAX INTEGER	{
				bypass(0),
				primary(1)
		}
	MAX-ACCESS read-only
	STATUS current
    DESCRIPTION
        "The Link State(Channel) Changed."
    ::= {link14OBPTrap 2}

-- 1.3.6.1.4.1.47477.10.21.14.3.50.3
	link14_R1WaveSet 	OBJECT-TYPE    
    SYNTAX INTEGER	{
				w1310nm(0),
				w1550nm(1)
		}
	MAX-ACCESS read-only
	STATUS current
    DESCRIPTION
        "Set The link14 R1 Wave."
    ::= {link14OBPTrap 3}

-- 1.3.6.1.4.1.47477.10.21.14.3.50.4
	link14_R2WaveSet 	OBJECT-TYPE    
    SYNTAX INTEGER	{
				w1310nm(0),
				w1550nm(1)
		}
	MAX-ACCESS read-only
	STATUS current
    DESCRIPTION
        "Set The link14 R2 Wave."
    ::= {link14OBPTrap 4}			

-- 1.3.6.1.4.1.47477.10.21.14.3.50.5
	link14_R3WaveSet 	OBJECT-TYPE    
    SYNTAX INTEGER	{
				w1310nm(0),
				w1550nm(1)
		}
	MAX-ACCESS read-only
	STATUS current
    DESCRIPTION
        "Set The link14 R3 Wave."
    ::= {link14OBPTrap 5}

-- 1.3.6.1.4.1.47477.10.21.14.3.50.6
	link14_R4WaveSet 	OBJECT-TYPE    
    SYNTAX INTEGER	{
				w1310nm(0),
				w1550nm(1)
		}
	MAX-ACCESS read-only
	STATUS current
    DESCRIPTION
        "Set The link14 R4 Wave."
    ::= {link14OBPTrap 6}	
	
-- 1.3.6.1.4.1.47477.10.21.14.3.50.7
	link14_R1AlarmSet 	OBJECT-TYPE    
    SYNTAX DisplayString
	MAX-ACCESS read-only
	STATUS current
    DESCRIPTION
        "Set The link14 R1 Alarm Threshold."
    ::= {link14OBPTrap 7}

-- 1.3.6.1.4.1.47477.10.21.14.3.50.8
	link14_R2AlarmSet 	OBJECT-TYPE    
    SYNTAX DisplayString
	MAX-ACCESS read-only
	STATUS current
    DESCRIPTION
        "Set The link14 R2 Alarm Threshold."
    ::= {link14OBPTrap 8}
	
-- 1.3.6.1.4.1.47477.10.21.14.3.50.9
	link14_R3AlarmSet 	OBJECT-TYPE    
    SYNTAX DisplayString
	MAX-ACCESS read-only
	STATUS current
    DESCRIPTION
        "Set The link14 R3 Alarm Threshold."
    ::= {link14OBPTrap 9}

-- 1.3.6.1.4.1.47477.10.21.14.3.50.10
	link14_R4AlarmSet 	OBJECT-TYPE    
    SYNTAX DisplayString
	MAX-ACCESS read-only
	STATUS current
    DESCRIPTION
        "Set The link14 R4 Alarm Threshold."
    ::= {link14OBPTrap 10}	
	
	
-- 1.3.6.1.4.1.47477.10.21.14.3.50.11
	link14_1R1AlarmSet 	OBJECT-TYPE    
    SYNTAX DisplayString
	MAX-ACCESS read-only
	STATUS current
    DESCRIPTION
        "Set The link14 1R1 Alarm Threshold."
    ::= {link14OBPTrap 11}

-- 1.3.6.1.4.1.47477.10.21.14.3.50.12
	link14_2R1AlarmSet 	OBJECT-TYPE    
    SYNTAX DisplayString
	MAX-ACCESS read-only
	STATUS current
    DESCRIPTION
        "Set The link14 2R1 Alarm Threshold."
    ::= {link14OBPTrap 12}
	
-- 1.3.6.1.4.1.47477.10.21.14.3.50.13
	link14_1R2AlarmSet 	OBJECT-TYPE    
    SYNTAX DisplayString
	MAX-ACCESS read-only
	STATUS current
    DESCRIPTION
        "Set The link14 1R2 Alarm Threshold."
    ::= {link14OBPTrap 13}

-- 1.3.6.1.4.1.47477.10.21.14.3.50.14
	link14_2R2AlarmSet 	OBJECT-TYPE    
    SYNTAX DisplayString
	MAX-ACCESS read-only
	STATUS current
    DESCRIPTION
        "Set The link14 2R2 Alarm Threshold."
    ::= {link14OBPTrap 14}
	
-- 1.3.6.1.4.1.47477.10.21.14.3.50.15
	link14_1R3AlarmSet 	OBJECT-TYPE    
    SYNTAX DisplayString
	MAX-ACCESS read-only
	STATUS current
    DESCRIPTION
        "Set The link14 1R3 Alarm Threshold."
    ::= {link14OBPTrap 15}

-- 1.3.6.1.4.1.47477.10.21.14.3.50.16
	link14_2R3AlarmSet 	OBJECT-TYPE    
    SYNTAX DisplayString
	MAX-ACCESS read-only
	STATUS current
    DESCRIPTION
        "Set The link14 2R3 Alarm Threshold."
    ::= {link14OBPTrap 16}
	
-- 1.3.6.1.4.1.47477.10.21.14.3.50.17
	link14_1R4AlarmSet 	OBJECT-TYPE    
    SYNTAX DisplayString
	MAX-ACCESS read-only
	STATUS current
    DESCRIPTION
        "Set The link14 1R4 Alarm Threshold."
    ::= {link14OBPTrap 17}

-- 1.3.6.1.4.1.47477.10.21.14.3.50.18
	link14_2R4AlarmSet 	OBJECT-TYPE    
    SYNTAX DisplayString
	MAX-ACCESS read-only
	STATUS current
    DESCRIPTION
        "Set The link14 2R4 Alarm Threshold."
    ::= {link14OBPTrap 18}
	
-- 1.3.6.1.4.1.47477.10.21.14.3.50.19
	link14_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link14 PowerAlarmBypass2 Changed."
    ::= {link14OBPTrap 19}
	
-- 1.3.6.1.4.1.47477.10.21.14.3.50.20
	link14_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link14 PowerAlarmBypass4 Changed."
    ::= {link14OBPTrap 20}	
	
-- 1.3.6.1.4.1.47477.10.21.14.3.50.21
	link14_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link14 PowerAlarmBypass8 Changed."
    ::= {link14OBPTrap 21}
	
-- 1.3.6.1.4.1.47477.10.21.14.3.50.22
	link14_powerAlarmR1 	OBJECT-TYPE    
    SYNTAX DisplayString
	MAX-ACCESS read-only
	STATUS current
    DESCRIPTION
        "Set The link14 R1 Power Status Alarm."
    ::= {link14OBPTrap 22}
	
-- 1.3.6.1.4.1.47477.10.21.14.3.50.23
	link14_powerAlarmR2 	OBJECT-TYPE    
    SYNTAX DisplayString
	MAX-ACCESS read-only
	STATUS current
    DESCRIPTION
        "Set The link14 R2 Power Status Alarm."
    ::= {link14OBPTrap 23}
	
-- 1.3.6.1.4.1.47477.10.21.14.3.50.24
	link14_powerAlarmR3 	OBJECT-TYPE    
    SYNTAX DisplayString
	MAX-ACCESS read-only
	STATUS current
    DESCRIPTION
        "Set The link14 R3 Power Status Alarm."
    ::= {link14OBPTrap 24}
	
-- 1.3.6.1.4.1.47477.10.21.14.3.50.25
	link14_powerAlarmR4 	OBJECT-TYPE    
    SYNTAX DisplayString
	MAX-ACCESS read-only
	STATUS current
    DESCRIPTION
        "Set The link14 R4 Power Status Alarm."
    ::= {link14OBPTrap 25}
	
	
-- 1.3.6.1.4.1.47477.10.21.14.3.50.26
	link14_powerAlarm1R1 	OBJECT-TYPE    
    SYNTAX DisplayString
	MAX-ACCESS read-only
	STATUS current
    DESCRIPTION
        "Set The link14 1R1 Power Status Alarm."
    ::= {link14OBPTrap 26}
	
-- 1.3.6.1.4.1.47477.10.21.14.3.50.27
	link14_powerAlarm2R1 	OBJECT-TYPE    
    SYNTAX DisplayString
	MAX-ACCESS read-only
	STATUS current
    DESCRIPTION
        "Set The link14 2R1 Power Status Alarm."
    ::= {link14OBPTrap 27}
	
-- 1.3.6.1.4.1.47477.10.21.14.3.50.28
	link14_powerAlarm1R2 	OBJECT-TYPE    
    SYNTAX DisplayString
	MAX-ACCESS read-only
	STATUS current
    DESCRIPTION
        "Set The link14 1R2 Power Status Alarm."
    ::= {link14OBPTrap 28}
	
-- 1.3.6.1.4.1.47477.10.21.14.3.50.29
	link14_powerAlarm2R2 	OBJECT-TYPE    
    SYNTAX DisplayString
	MAX-ACCESS read-only
	STATUS current
    DESCRIPTION
        "Set The link14 2R2 Power Status Alarm."
    ::= {link14OBPTrap 29}
	
-- 1.3.6.1.4.1.47477.10.21.14.3.50.30
	link14_powerAlarm1R3 	OBJECT-TYPE    
    SYNTAX DisplayString
	MAX-ACCESS read-only
	STATUS current
    DESCRIPTION
        "Set The link14 1R3 Power Status Alarm."
    ::= {link14OBPTrap 30}
	
-- 1.3.6.1.4.1.47477.10.21.14.3.50.31
	link14_powerAlarm2R3 	OBJECT-TYPE    
    SYNTAX DisplayString
	MAX-ACCESS read-only
	STATUS current
    DESCRIPTION
        "Set The link14 2R1 Power Status Alarm."
    ::= {link14OBPTrap 31}
	
-- 1.3.6.1.4.1.47477.10.21.14.3.50.32
	link14_powerAlarm1R4 	OBJECT-TYPE    
    SYNTAX DisplayString
	MAX-ACCESS read-only
	STATUS current
    DESCRIPTION
        "Set The link14 1R4 Power Status Alarm."
    ::= {link14OBPTrap 32}
	
-- 1.3.6.1.4.1.47477.10.21.14.3.50.33
	link14_powerAlarm2R4 	OBJECT-TYPE    
    SYNTAX DisplayString
	MAX-ACCESS read-only
	STATUS current
    DESCRIPTION
        "Set The link14 2R4 Power Status Alarm."
    ::= {link14OBPTrap 33}
	
--  1.3.6.1.4.1.47477.10.21.15.3.1
		-- 1.3.6.1.4.1.47477.10.21.15.3.1
		link15_State OBJECT-TYPE
			SYNTAX INTEGER
				{
				off(0),
				on(1)
				}
			MAX-ACCESS read-only
			STATUS current
			DESCRIPTION
				"get the information about whether link15 is working."
			::= { link15OBP 1 }

		
--  1.3.6.1.4.1.47477.10.21.15.3.2
		-- 1.3.6.1.4.1.47477.10.21.15.3.2
		link15_DeviceType OBJECT-TYPE
			SYNTAX DisplayString
			MAX-ACCESS read-only
			STATUS current
			DESCRIPTION
				"get the type of card in link15."
			::= { link15OBP 2 }

			
--  1.3.6.1.4.1.47477.10.21.15.3.3
		-- 1.3.6.1.4.1.47477.10.21.15.3.3
		link15_WorkMode OBJECT-TYPE
			SYNTAX INTEGER
				{
				manualMode(0),
				autoMode(1)
				}
			MAX-ACCESS read-write
			STATUS current
			DESCRIPTION
				"get or set link15's work mode."
			::= { link15OBP 3 }

		
--  1.3.6.1.4.1.47477.10.21.15.3.4
		-- 1.3.6.1.4.1.47477.10.21.15.3.4
		link15_Channel OBJECT-TYPE
			SYNTAX INTEGER
				{
				bypass(0),
				primary(1)
				}
			MAX-ACCESS read-write
			STATUS current
			DESCRIPTION
				"get or set the channel in which link15 works."
			::= { link15OBP 4 }


--  1.3.6.1.4.1.47477.10.21.15.3.5
		-- 1.3.6.1.4.1.47477.10.21.15.3.5
		link15_R1Power OBJECT-TYPE
			SYNTAX DisplayString
			MAX-ACCESS read-only
			STATUS current
			DESCRIPTION
				"get the power of R1 in link15."
			::= { link15OBP 5 }

		
--  1.3.6.1.4.1.47477.10.21.15.3.6
		-- 1.3.6.1.4.1.47477.10.21.15.3.6
		link15_R2Power OBJECT-TYPE
			SYNTAX DisplayString
			MAX-ACCESS read-only
			STATUS current
			DESCRIPTION
				"get the power of R2 in link15."
			::= { link15OBP 6 }
			
--  1.3.6.1.4.1.47477.10.21.15.3.35
		-- 1.3.6.1.4.1.47477.10.21.15.3.35
		link15_R3Power OBJECT-TYPE
			SYNTAX DisplayString
			MAX-ACCESS read-only
			STATUS current
			DESCRIPTION
				"get the power of R3 in link15."
			::= { link15OBP 35 }
			
--  1.3.6.1.4.1.47477.10.21.15.3.36
		-- 1.3.6.1.4.1.47477.10.21.15.3.36
		link15_R4Power OBJECT-TYPE
			SYNTAX DisplayString
			MAX-ACCESS read-only
			STATUS current
			DESCRIPTION
				"get the power of R4 in link15."
			::= { link15OBP 36 }		
		
--  1.3.6.1.4.1.47477.10.21.15.3.7
		-- 1.3.6.1.4.1.47477.10.21.15.3.7
		link15_R1Wave OBJECT-TYPE
			SYNTAX INTEGER
				{
				w1310nm(0),
				w1550nm(1),
				na(2)
				}
			MAX-ACCESS read-write
			STATUS current
			DESCRIPTION
				"get or set the wave length of R1 in link15."
			::= { link15OBP 7 }

		
--  1.3.6.1.4.1.47477.10.21.15.3.8
		-- 1.3.6.1.4.1.47477.10.21.15.3.8
		link15_R2Wave OBJECT-TYPE
			SYNTAX INTEGER
				{
				w1310nm(0),
				w1550nm(1),
				na(2)
				}
			MAX-ACCESS read-write
			STATUS current
			DESCRIPTION
				"get or set the wave length of R2 in link15."
			::= { link15OBP 8 }


--  1.3.6.1.4.1.47477.10.21.15.3.27
		-- 1.3.6.1.4.1.47477.10.21.15.3.27
		link15_R3Wave OBJECT-TYPE
			SYNTAX INTEGER
				{
				w1310nm(0),
				w1550nm(1),
				na(2)
				}
			MAX-ACCESS read-write
			STATUS current
			DESCRIPTION
				"get or set the wave length of R3 in link15."
			::= { link15OBP 27 }

		
--  1.3.6.1.4.1.47477.10.21.15.3.28
		-- 1.3.6.1.4.1.47477.10.21.15.3.28
		link15_R4Wave OBJECT-TYPE
			SYNTAX INTEGER
				{
				w1310nm(0),
				w1550nm(1),
				na(2)
				}
			MAX-ACCESS read-write
			STATUS current
			DESCRIPTION
				"get or set the wave length of R4 in link15."
			::= { link15OBP 28 }
			
--  1.3.6.1.4.1.47477.10.21.15.3.9
		-- 1.3.6.1.4.1.47477.10.21.15.3.9
		link15_R1AlarmPower OBJECT-TYPE
			SYNTAX DisplayString
			MAX-ACCESS read-write
			STATUS current
			DESCRIPTION
				"get or set the power alarm threshold of R1 in link15."
			::= { link15OBP 9 }

		
--  1.3.6.1.4.1.47477.10.21.15.3.10
		-- 1.3.6.1.4.1.47477.10.21.15.3.10
		link15_R2AlarmPower OBJECT-TYPE
			SYNTAX DisplayString
			MAX-ACCESS read-write
			STATUS current
			DESCRIPTION
				"get or set the power alarm threshold of R2 in link15."
			::= { link15OBP 10 }


--  1.3.6.1.4.1.47477.10.21.15.3.29
		-- 1.3.6.1.4.1.47477.10.21.15.3.29
		link15_R3AlarmPower OBJECT-TYPE
			SYNTAX DisplayString
			MAX-ACCESS read-write
			STATUS current
			DESCRIPTION
				"get or set the power alarm threshold of R3 in link15."
			::= { link15OBP 29 }

		
--  1.3.6.1.4.1.47477.10.21.15.3.30
		-- 1.3.6.1.4.1.47477.10.21.15.3.30
		link15_R4AlarmPower OBJECT-TYPE
			SYNTAX DisplayString
			MAX-ACCESS read-write
			STATUS current
			DESCRIPTION
				"get or set the power alarm threshold of R4 in link15."
			::= { link15OBP 30 }

-- OBP4
--  1.3.6.1.4.1.47477.10.21.15.3.37
		-- 1.3.6.1.4.1.47477.10.21.15.3.37
		link15_1R1Power OBJECT-TYPE
			SYNTAX DisplayString
			MAX-ACCESS read-only
			STATUS current
			DESCRIPTION
				"get the power of 1R1 in link15."
			::= { link15OBP 37 }
			
--  1.3.6.1.4.1.47477.10.21.15.3.38
		-- 1.3.6.1.4.1.47477.10.21.15.3.38
		link15_1R2Power OBJECT-TYPE
			SYNTAX DisplayString
			MAX-ACCESS read-only
			STATUS current
			DESCRIPTION
				"get the power of 1R2 in link15."
			::= { link15OBP 38 }

--  1.3.6.1.4.1.47477.10.21.15.3.39
		-- 1.3.6.1.4.1.47477.10.21.15.3.39
		link15_1R3Power OBJECT-TYPE
			SYNTAX DisplayString
			MAX-ACCESS read-only
			STATUS current
			DESCRIPTION
				"get the power of 1R3 in link15."
			::= { link15OBP 39 }
			
--  1.3.6.1.4.1.47477.10.21.15.3.40
		-- 1.3.6.1.4.1.47477.10.21.15.3.40
		link15_1R4Power OBJECT-TYPE
			SYNTAX DisplayString
			MAX-ACCESS read-only
			STATUS current
			DESCRIPTION
				"get the power of 1R4 in link15."
			::= { link15OBP 40 }

--  1.3.6.1.4.1.47477.10.21.15.3.41
		-- 1.3.6.1.4.1.47477.10.21.15.3.41
		link15_2R1Power OBJECT-TYPE
			SYNTAX DisplayString
			MAX-ACCESS read-only
			STATUS current
			DESCRIPTION
				"get the power of 2R1 in link15."
			::= { link15OBP 41 }
			
--  1.3.6.1.4.1.47477.10.21.15.3.42
		-- 1.3.6.1.4.1.47477.10.21.15.3.42
		link15_2R2Power OBJECT-TYPE
			SYNTAX DisplayString
			MAX-ACCESS read-only
			STATUS current
			DESCRIPTION
				"get the power of 2R2 in link15."
			::= { link15OBP 42 }

--  1.3.6.1.4.1.47477.10.21.15.3.41
		-- 1.3.6.1.4.1.47477.10.21.15.3.43
		link15_2R3Power OBJECT-TYPE
			SYNTAX DisplayString
			MAX-ACCESS read-only
			STATUS current
			DESCRIPTION
				"get the power of 2R3 in link15."
			::= { link15OBP 43 }
			
--  1.3.6.1.4.1.47477.10.21.15.3.42
		-- 1.3.6.1.4.1.47477.10.21.15.3.44
		link15_2R4Power OBJECT-TYPE
			SYNTAX DisplayString
			MAX-ACCESS read-only
			STATUS current
			DESCRIPTION
				"get the power of 2R4 in link15."
			::= { link15OBP 44 }
			
--  1.3.6.1.4.1.47477.10.21.15.3.49
		-- 1.3.6.1.4.1.47477.10.21.15.3.49
		link15_1R1Wave OBJECT-TYPE
			SYNTAX INTEGER
				{
				w850nm(0),
				na(2)
				}
			MAX-ACCESS read-only
			STATUS current
			DESCRIPTION
				"get the wave length of 1R1 in link15."
			::= { link15OBP 49 }
		
--  1.3.6.1.4.1.47477.10.21.15.3.60
		-- 1.3.6.1.4.1.47477.10.21.15.3.60
		link15_1R2Wave OBJECT-TYPE
			SYNTAX INTEGER
				{
				w850nm(0),
				na(2)
				}
			MAX-ACCESS read-only
			STATUS current
			DESCRIPTION
				"get the wave length of 1R2 in link15."
			::= { link15OBP 60 }

--  1.3.6.1.4.1.47477.10.21.15.3.61
		-- 1.3.6.1.4.1.47477.10.21.15.3.61
		link15_1R3Wave OBJECT-TYPE
			SYNTAX INTEGER
				{
				w850nm(0),
				na(2)
				}
			MAX-ACCESS read-only
			STATUS current
			DESCRIPTION
				"get the wave length of 1R3 in link15."
			::= { link15OBP 61 }

		
--  1.3.6.1.4.1.47477.10.21.15.3.62
		-- 1.3.6.1.4.1.47477.10.21.15.3.62
		link15_1R4Wave OBJECT-TYPE
			SYNTAX INTEGER
				{
				w850nm(0),
				na(2)
				}
			MAX-ACCESS read-only
			STATUS current
			DESCRIPTION
				"get the wave length of 1R4 in link15."
			::= { link15OBP 62 }
	
--  1.3.6.1.4.1.47477.10.21.15.3.63
		-- 1.3.6.1.4.1.47477.10.21.15.3.63
		link15_2R1Wave OBJECT-TYPE
			SYNTAX INTEGER
				{
				w850nm(0),
				na(2)
				}
			MAX-ACCESS read-only
			STATUS current
			DESCRIPTION
				"get the wave length of 2R1 in link15."
			::= { link15OBP 63 }

		
--  1.3.6.1.4.1.47477.10.21.15.3.64
		-- 1.3.6.1.4.1.47477.10.21.15.3.64
		link15_2R2Wave OBJECT-TYPE
			SYNTAX INTEGER
				{
				w850nm(0),
				na(2)
				}
			MAX-ACCESS read-only
			STATUS current
			DESCRIPTION
				"get the wave length of 2R2 in link15."
			::= { link15OBP 64 }	
	
--  1.3.6.1.4.1.47477.10.21.15.3.65
		-- 1.3.6.1.4.1.47477.10.21.15.3.65
		link15_2R3Wave OBJECT-TYPE
			SYNTAX INTEGER
				{
				w850nm(0),
				na(2)
				}
			MAX-ACCESS read-only
			STATUS current
			DESCRIPTION
				"get the wave length of 2R3 in link15."
			::= { link15OBP 65 }

		
--  1.3.6.1.4.1.47477.10.21.15.3.66
		-- 1.3.6.1.4.1.47477.10.21.15.3.66
		link15_2R4Wave OBJECT-TYPE
			SYNTAX INTEGER
				{
				w850nm(0),
				na(2)
				}
			MAX-ACCESS read-only
			STATUS current
			DESCRIPTION
				"get the wave length of 2R4 in link15."
			::= { link15OBP 66 }	
			
--  1.3.6.1.4.1.47477.10.21.15.3.31
		-- 1.3.6.1.4.1.47477.10.21.15.3.31
		link15_1R1AlarmPower OBJECT-TYPE
			SYNTAX DisplayString
			MAX-ACCESS read-write
			STATUS current
			DESCRIPTION
				"get or set the power alarm threshold of 1R1 in link15."
			::= { link15OBP 31 }
			
--  1.3.6.1.4.1.47477.10.21.15.3.32
		-- 1.3.6.1.4.1.47477.10.21.15.3.32
		link15_1R2AlarmPower OBJECT-TYPE
			SYNTAX DisplayString
			MAX-ACCESS read-write
			STATUS current
			DESCRIPTION
				"get or set the power alarm threshold of 1R2 in link15."
			::= { link15OBP 32 }

--  1.3.6.1.4.1.47477.10.21.15.3.33
		-- 1.3.6.1.4.1.47477.10.21.15.3.33
		link15_1R3AlarmPower OBJECT-TYPE
			SYNTAX DisplayString
			MAX-ACCESS read-write
			STATUS current
			DESCRIPTION
				"get or set the power alarm threshold of 1R3 in link15."
			::= { link15OBP 33 }
			
--  1.3.6.1.4.1.47477.10.21.15.3.34
		-- 1.3.6.1.4.1.47477.10.21.15.3.34
		link15_1R4AlarmPower OBJECT-TYPE
			SYNTAX DisplayString
			MAX-ACCESS read-write
			STATUS current
			DESCRIPTION
				"get or set the power alarm threshold of 1R4 in link15."
			::= { link15OBP 34 }

--  1.3.6.1.4.1.47477.10.21.15.3.45
		-- 1.3.6.1.4.1.47477.10.21.15.3.45
		link15_2R1AlarmPower OBJECT-TYPE
			SYNTAX DisplayString
			MAX-ACCESS read-write
			STATUS current
			DESCRIPTION
				"get or set the power alarm threshold of 2R1 in link15."
			::= { link15OBP 45 }
			
--  1.3.6.1.4.1.47477.10.21.15.3.46
		-- 1.3.6.1.4.1.47477.10.21.15.3.46
		link15_2R2AlarmPower OBJECT-TYPE
			SYNTAX DisplayString
			MAX-ACCESS read-write
			STATUS current
			DESCRIPTION
				"get or set the power alarm threshold of 2R2 in link15."
			::= { link15OBP 46 }

--  1.3.6.1.4.1.47477.10.21.15.3.47
		-- 1.3.6.1.4.1.47477.10.21.15.3.47
		link15_2R3AlarmPower OBJECT-TYPE
			SYNTAX DisplayString
			MAX-ACCESS read-write
			STATUS current
			DESCRIPTION
				"get or set the power alarm threshold of 2R3 in link15."
			::= { link15OBP 47 }
			
--  1.3.6.1.4.1.47477.10.21.15.3.48
		-- 1.3.6.1.4.1.47477.10.21.15.3.48
		link15_2R4AlarmPower OBJECT-TYPE
			SYNTAX DisplayString
			MAX-ACCESS read-write
			STATUS current
			DESCRIPTION
				"get or set the power alarm threshold of 2R4 in link15."
			::= { link15OBP 48 }
			
--  1.3.6.1.4.1.47477.10.21.15.3.11
		-- 1.3.6.1.4.1.47477.10.21.15.3.11
		link15_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link15OBP 11 }
			
--  1.3.6.1.4.1.47477.10.21.15.3.67
		-- 1.3.6.1.4.1.47477.10.21.15.3.67
		link15_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link15OBP 67 }
			
--  1.3.6.1.4.1.47477.10.21.15.3.68
		-- 1.3.6.1.4.1.47477.10.21.15.3.68
		link15_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link15OBP 68 }
			
--  1.3.6.1.4.1.47477.10.21.15.3.12
		-- 1.3.6.1.4.1.47477.10.21.15.3.12
		link15_ReturnDelay OBJECT-TYPE
			--SYNTAX Integer32
			SYNTAX Integer32
			MAX-ACCESS read-write
			STATUS current
			DESCRIPTION
				"get or set how long link15 takes to return to automatic mode."
			::= { link15OBP 12 }
			
--  1.3.6.1.4.1.47477.10.21.15.3.13
		-- 1.3.6.1.4.1.47477.10.21.15.3.13
		link15_BackMode OBJECT-TYPE
			SYNTAX INTEGER
				{
				autoNoBack(0),
				autoBack(1)
				}
			MAX-ACCESS read-write
			STATUS current
			DESCRIPTION
				"get or set the back mode of link15."
			::= { link15OBP 13 }

		
--  1.3.6.1.4.1.47477.10.21.15.3.14
		-- 1.3.6.1.4.1.47477.10.21.15.3.14
		link15_BackDelay OBJECT-TYPE
			SYNTAX Integer32
			MAX-ACCESS read-write
			STATUS current
			DESCRIPTION
				"get or set the back delay."
			::= { link15OBP 14 }

--  1.3.6.1.4.1.47477.10.21.15.3.15
		-- 1.3.6.1.4.1.47477.10.21.15.3.15
		link15_ActiveHeartSwitch OBJECT-TYPE
			SYNTAX INTEGER
				{
				off(0),
				on(1)
				}
			MAX-ACCESS read-write
			STATUS current
			DESCRIPTION
				"get or set the switch status of active heartbeat."
			::= { link15OBP 15 }

		
--  1.3.6.1.4.1.47477.10.21.15.3.16
		-- 1.3.6.1.4.1.47477.10.21.15.3.16
		link15_ActiveSendInterval OBJECT-TYPE
			SYNTAX Integer32
			MAX-ACCESS read-write
			STATUS current
			DESCRIPTION
				"get or set the send interval of active heartbeat."
			::= { link15OBP 16 }		

--  1.3.6.1.4.1.47477.10.21.15.3.17
		-- 1.3.6.1.4.1.47477.10.21.15.3.17
		link15_ActiveTimeOut OBJECT-TYPE
			SYNTAX Integer32
			MAX-ACCESS read-write
			STATUS current
			DESCRIPTION
				"get or set how long the active heartbeat send timeout."
			::= { link15OBP 17 }

--  1.3.6.1.4.1.47477.10.21.15.3.18
		-- 1.3.6.1.4.1.47477.10.21.15.3.18
		link15_ActiveLossBypass OBJECT-TYPE
			SYNTAX Integer32
			MAX-ACCESS read-write
			STATUS current
			DESCRIPTION
				"get or set the bypass for active heartbeat packet loss."
			::= { link15OBP 18 }

--  1.3.6.1.4.1.47477.10.21.15.3.19
		-- 1.3.6.1.4.1.47477.10.21.15.3.19
		link15_PingIpAddress OBJECT-TYPE
			SYNTAX IpAddress
			MAX-ACCESS read-write
			STATUS current
			DESCRIPTION
				"get or set the ping ip address of link15."
			::= { link15OBP 19 }

--  1.3.6.1.4.1.47477.10.21.15.3.20
		-- 1.3.6.1.4.1.47477.10.21.15.3.20
		link15_PassiveHeartSwitch OBJECT-TYPE
			SYNTAX INTEGER
				{
				off(0),
				on(1)
				}
			MAX-ACCESS read-write
			STATUS current
			DESCRIPTION
				"get or set the switch status of passive heartbeat."
			::= { link15OBP 20 }
	

--  1.3.6.1.4.1.47477.10.21.15.3.21
		-- 1.3.6.1.4.1.47477.10.21.15.3.21
		link15_PassiveTimeOut OBJECT-TYPE
			SYNTAX Integer32
			MAX-ACCESS read-write
			STATUS current
			DESCRIPTION
				"get or set how long the passive heartbeat send timeout."
			::= { link15OBP 21 }

--  1.3.6.1.4.1.47477.10.21.15.3.22
		-- 1.3.6.1.4.1.47477.10.21.15.3.22
		link15_PassiveLossBypass OBJECT-TYPE
			SYNTAX Integer32
			MAX-ACCESS read-write
			STATUS current
			DESCRIPTION
				"get or set the bypass for passive heartbeat packet loss."
			::= { link15OBP 22 }

--  1.3.6.1.4.1.47477.10.21.15.3.23
		-- 1.3.6.1.4.1.47477.10.21.15.3.23
		link15_SwitchProtect OBJECT-TYPE
			SYNTAX INTEGER
				{
				off(0),
				on(1)
				}
			MAX-ACCESS read-write
			STATUS current
			DESCRIPTION
				"get or set the switch protection status of link15."
			::= { link15OBP 23 }
			
--  1.3.6.1.4.1.47477.10.21.15.3.24
		-- 1.3.6.1.4.1.47477.10.21.15.3.24
		link15_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link15OBP 24 }		

--  1.3.6.1.4.1.47477.10.21.15.3.25
		-- 1.3.6.1.4.1.47477.10.21.15.3.25
		link15_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link15OBP 25 }	

--  1.3.6.1.4.1.47477.10.21.15.3.26
		-- 1.3.6.1.4.1.47477.10.21.15.3.26
		link15_PowerAlarmStatus OBJECT-TYPE
			SYNTAX INTEGER
				{
				off(0),
				alarm(1),
				normal(2),
				na(3)
				}
			MAX-ACCESS read-only
			STATUS current
			DESCRIPTION
				"get whether a power alarm is generated."
			::= { link15OBP 26 }	


-- 1.3.6.1.4.1.47477.10.21.15.3.50.1
	link15_WorkModeChange 	OBJECT-TYPE    
    SYNTAX INTEGER	{
				manualMode(0),
				autoMode(1)
		}
	MAX-ACCESS read-only
	STATUS current
    DESCRIPTION
        "The Link mode Changed."
    ::= {link15OBPTrap 1}

-- 1.3.6.1.4.1.47477.10.21.15.3.50.2
	link15_StateChange 	OBJECT-TYPE    
    SYNTAX INTEGER	{
				bypass(0),
				primary(1)
		}
	MAX-ACCESS read-only
	STATUS current
    DESCRIPTION
        "The Link State(Channel) Changed."
    ::= {link15OBPTrap 2}

-- 1.3.6.1.4.1.47477.10.21.15.3.50.3
	link15_R1WaveSet 	OBJECT-TYPE    
    SYNTAX INTEGER	{
				w1310nm(0),
				w1550nm(1)
		}
	MAX-ACCESS read-only
	STATUS current
    DESCRIPTION
        "Set The link15 R1 Wave."
    ::= {link15OBPTrap 3}

-- 1.3.6.1.4.1.47477.10.21.15.3.50.4
	link15_R2WaveSet 	OBJECT-TYPE    
    SYNTAX INTEGER	{
				w1310nm(0),
				w1550nm(1)
		}
	MAX-ACCESS read-only
	STATUS current
    DESCRIPTION
        "Set The link15 R2 Wave."
    ::= {link15OBPTrap 4}			

-- 1.3.6.1.4.1.47477.10.21.15.3.50.5
	link15_R3WaveSet 	OBJECT-TYPE    
    SYNTAX INTEGER	{
				w1310nm(0),
				w1550nm(1)
		}
	MAX-ACCESS read-only
	STATUS current
    DESCRIPTION
        "Set The link15 R3 Wave."
    ::= {link15OBPTrap 5}

-- 1.3.6.1.4.1.47477.10.21.15.3.50.6
	link15_R4WaveSet 	OBJECT-TYPE    
    SYNTAX INTEGER	{
				w1310nm(0),
				w1550nm(1)
		}
	MAX-ACCESS read-only
	STATUS current
    DESCRIPTION
        "Set The link15 R4 Wave."
    ::= {link15OBPTrap 6}	
	
-- 1.3.6.1.4.1.47477.10.21.15.3.50.7
	link15_R1AlarmSet 	OBJECT-TYPE    
    SYNTAX DisplayString
	MAX-ACCESS read-only
	STATUS current
    DESCRIPTION
        "Set The link15 R1 Alarm Threshold."
    ::= {link15OBPTrap 7}

-- 1.3.6.1.4.1.47477.10.21.15.3.50.8
	link15_R2AlarmSet 	OBJECT-TYPE    
    SYNTAX DisplayString
	MAX-ACCESS read-only
	STATUS current
    DESCRIPTION
        "Set The link15 R2 Alarm Threshold."
    ::= {link15OBPTrap 8}
	
-- 1.3.6.1.4.1.47477.10.21.15.3.50.9
	link15_R3AlarmSet 	OBJECT-TYPE    
    SYNTAX DisplayString
	MAX-ACCESS read-only
	STATUS current
    DESCRIPTION
        "Set The link15 R3 Alarm Threshold."
    ::= {link15OBPTrap 9}

-- 1.3.6.1.4.1.47477.10.21.15.3.50.10
	link15_R4AlarmSet 	OBJECT-TYPE    
    SYNTAX DisplayString
	MAX-ACCESS read-only
	STATUS current
    DESCRIPTION
        "Set The link15 R4 Alarm Threshold."
    ::= {link15OBPTrap 10}	
	
	
-- 1.3.6.1.4.1.47477.10.21.15.3.50.11
	link15_1R1AlarmSet 	OBJECT-TYPE    
    SYNTAX DisplayString
	MAX-ACCESS read-only
	STATUS current
    DESCRIPTION
        "Set The link15 1R1 Alarm Threshold."
    ::= {link15OBPTrap 11}

-- 1.3.6.1.4.1.47477.10.21.15.3.50.12
	link15_2R1AlarmSet 	OBJECT-TYPE    
    SYNTAX DisplayString
	MAX-ACCESS read-only
	STATUS current
    DESCRIPTION
        "Set The link15 2R1 Alarm Threshold."
    ::= {link15OBPTrap 12}
	
-- 1.3.6.1.4.1.47477.10.21.15.3.50.13
	link15_1R2AlarmSet 	OBJECT-TYPE    
    SYNTAX DisplayString
	MAX-ACCESS read-only
	STATUS current
    DESCRIPTION
        "Set The link15 1R2 Alarm Threshold."
    ::= {link15OBPTrap 13}

-- 1.3.6.1.4.1.47477.10.21.15.3.50.14
	link15_2R2AlarmSet 	OBJECT-TYPE    
    SYNTAX DisplayString
	MAX-ACCESS read-only
	STATUS current
    DESCRIPTION
        "Set The link15 2R2 Alarm Threshold."
    ::= {link15OBPTrap 14}
	
-- 1.3.6.1.4.1.47477.10.21.15.3.50.15
	link15_1R3AlarmSet 	OBJECT-TYPE    
    SYNTAX DisplayString
	MAX-ACCESS read-only
	STATUS current
    DESCRIPTION
        "Set The link15 1R3 Alarm Threshold."
    ::= {link15OBPTrap 15}

-- 1.3.6.1.4.1.47477.10.21.15.3.50.16
	link15_2R3AlarmSet 	OBJECT-TYPE    
    SYNTAX DisplayString
	MAX-ACCESS read-only
	STATUS current
    DESCRIPTION
        "Set The link15 2R3 Alarm Threshold."
    ::= {link15OBPTrap 16}
	
-- 1.3.6.1.4.1.47477.10.21.15.3.50.17
	link15_1R4AlarmSet 	OBJECT-TYPE    
    SYNTAX DisplayString
	MAX-ACCESS read-only
	STATUS current
    DESCRIPTION
        "Set The link15 1R4 Alarm Threshold."
    ::= {link15OBPTrap 17}

-- 1.3.6.1.4.1.47477.10.21.15.3.50.18
	link15_2R4AlarmSet 	OBJECT-TYPE    
    SYNTAX DisplayString
	MAX-ACCESS read-only
	STATUS current
    DESCRIPTION
        "Set The link15 2R4 Alarm Threshold."
    ::= {link15OBPTrap 18}
	
-- 1.3.6.1.4.1.47477.10.21.15.3.50.19
	link15_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link15 PowerAlarmBypass2 Changed."
    ::= {link15OBPTrap 19}
	
-- 1.3.6.1.4.1.47477.10.21.15.3.50.20
	link15_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link15 PowerAlarmBypass4 Changed."
    ::= {link15OBPTrap 20}	
	
-- 1.3.6.1.4.1.47477.10.21.15.3.50.21
	link15_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link15 PowerAlarmBypass8 Changed."
    ::= {link15OBPTrap 21}
	
-- 1.3.6.1.4.1.47477.10.21.15.3.50.22
	link15_powerAlarmR1 	OBJECT-TYPE    
    SYNTAX DisplayString
	MAX-ACCESS read-only
	STATUS current
    DESCRIPTION
        "Set The link15 R1 Power Status Alarm."
    ::= {link15OBPTrap 22}
	
-- 1.3.6.1.4.1.47477.10.21.15.3.50.23
	link15_powerAlarmR2 	OBJECT-TYPE    
    SYNTAX DisplayString
	MAX-ACCESS read-only
	STATUS current
    DESCRIPTION
        "Set The link15 R2 Power Status Alarm."
    ::= {link15OBPTrap 23}
	
-- 1.3.6.1.4.1.47477.10.21.15.3.50.24
	link15_powerAlarmR3 	OBJECT-TYPE    
    SYNTAX DisplayString
	MAX-ACCESS read-only
	STATUS current
    DESCRIPTION
        "Set The link15 R3 Power Status Alarm."
    ::= {link15OBPTrap 24}
	
-- 1.3.6.1.4.1.47477.10.21.15.3.50.25
	link15_powerAlarmR4 	OBJECT-TYPE    
    SYNTAX DisplayString
	MAX-ACCESS read-only
	STATUS current
    DESCRIPTION
        "Set The link15 R4 Power Status Alarm."
    ::= {link15OBPTrap 25}
	
	
-- 1.3.6.1.4.1.47477.10.21.15.3.50.26
	link15_powerAlarm1R1 	OBJECT-TYPE    
    SYNTAX DisplayString
	MAX-ACCESS read-only
	STATUS current
    DESCRIPTION
        "Set The link15 1R1 Power Status Alarm."
    ::= {link15OBPTrap 26}
	
-- 1.3.6.1.4.1.47477.10.21.15.3.50.27
	link15_powerAlarm2R1 	OBJECT-TYPE    
    SYNTAX DisplayString
	MAX-ACCESS read-only
	STATUS current
    DESCRIPTION
        "Set The link15 2R1 Power Status Alarm."
    ::= {link15OBPTrap 27}
	
-- 1.3.6.1.4.1.47477.10.21.15.3.50.28
	link15_powerAlarm1R2 	OBJECT-TYPE    
    SYNTAX DisplayString
	MAX-ACCESS read-only
	STATUS current
    DESCRIPTION
        "Set The link15 1R2 Power Status Alarm."
    ::= {link15OBPTrap 28}
	
-- 1.3.6.1.4.1.47477.10.21.15.3.50.29
	link15_powerAlarm2R2 	OBJECT-TYPE    
    SYNTAX DisplayString
	MAX-ACCESS read-only
	STATUS current
    DESCRIPTION
        "Set The link15 2R2 Power Status Alarm."
    ::= {link15OBPTrap 29}
	
-- 1.3.6.1.4.1.47477.10.21.15.3.50.30
	link15_powerAlarm1R3 	OBJECT-TYPE    
    SYNTAX DisplayString
	MAX-ACCESS read-only
	STATUS current
    DESCRIPTION
        "Set The link15 1R3 Power Status Alarm."
    ::= {link15OBPTrap 30}
	
-- 1.3.6.1.4.1.47477.10.21.15.3.50.31
	link15_powerAlarm2R3 	OBJECT-TYPE    
    SYNTAX DisplayString
	MAX-ACCESS read-only
	STATUS current
    DESCRIPTION
        "Set The link15 2R1 Power Status Alarm."
    ::= {link15OBPTrap 31}
	
-- 1.3.6.1.4.1.47477.10.21.15.3.50.32
	link15_powerAlarm1R4 	OBJECT-TYPE    
    SYNTAX DisplayString
	MAX-ACCESS read-only
	STATUS current
    DESCRIPTION
        "Set The link15 1R4 Power Status Alarm."
    ::= {link15OBPTrap 32}
	
-- 1.3.6.1.4.1.47477.10.21.15.3.50.33
	link15_powerAlarm2R4 	OBJECT-TYPE    
    SYNTAX DisplayString
	MAX-ACCESS read-only
	STATUS current
    DESCRIPTION
        "Set The link15 2R4 Power Status Alarm."
    ::= {link15OBPTrap 33}
	
--  1.3.6.1.4.1.47477.10.21.16.3.1
		-- 1.3.6.1.4.1.47477.10.21.16.3.1
		link16_State OBJECT-TYPE
			SYNTAX INTEGER
				{
				off(0),
				on(1)
				}
			MAX-ACCESS read-only
			STATUS current
			DESCRIPTION
				"get the information about whether link16 is working."
			::= { link16OBP 1 }

		
--  1.3.6.1.4.1.47477.10.21.16.3.2
		-- 1.3.6.1.4.1.47477.10.21.16.3.2
		link16_DeviceType OBJECT-TYPE
			SYNTAX DisplayString
			MAX-ACCESS read-only
			STATUS current
			DESCRIPTION
				"get the type of card in link16."
			::= { link16OBP 2 }

			
--  1.3.6.1.4.1.47477.10.21.16.3.3
		-- 1.3.6.1.4.1.47477.10.21.16.3.3
		link16_WorkMode OBJECT-TYPE
			SYNTAX INTEGER
				{
				manualMode(0),
				autoMode(1)
				}
			MAX-ACCESS read-write
			STATUS current
			DESCRIPTION
				"get or set link16's work mode."
			::= { link16OBP 3 }

		
--  1.3.6.1.4.1.47477.10.21.16.3.4
		-- 1.3.6.1.4.1.47477.10.21.16.3.4
		link16_Channel OBJECT-TYPE
			SYNTAX INTEGER
				{
				bypass(0),
				primary(1)
				}
			MAX-ACCESS read-write
			STATUS current
			DESCRIPTION
				"get or set the channel in which link16 works."
			::= { link16OBP 4 }


--  1.3.6.1.4.1.47477.10.21.16.3.5
		-- 1.3.6.1.4.1.47477.10.21.16.3.5
		link16_R1Power OBJECT-TYPE
			SYNTAX DisplayString
			MAX-ACCESS read-only
			STATUS current
			DESCRIPTION
				"get the power of R1 in link16."
			::= { link16OBP 5 }

		
--  1.3.6.1.4.1.47477.10.21.16.3.6
		-- 1.3.6.1.4.1.47477.10.21.16.3.6
		link16_R2Power OBJECT-TYPE
			SYNTAX DisplayString
			MAX-ACCESS read-only
			STATUS current
			DESCRIPTION
				"get the power of R2 in link16."
			::= { link16OBP 6 }
			
--  1.3.6.1.4.1.47477.10.21.16.3.35
		-- 1.3.6.1.4.1.47477.10.21.16.3.35
		link16_R3Power OBJECT-TYPE
			SYNTAX DisplayString
			MAX-ACCESS read-only
			STATUS current
			DESCRIPTION
				"get the power of R3 in link16."
			::= { link16OBP 35 }
			
--  1.3.6.1.4.1.47477.10.21.16.3.36
		-- 1.3.6.1.4.1.47477.10.21.16.3.36
		link16_R4Power OBJECT-TYPE
			SYNTAX DisplayString
			MAX-ACCESS read-only
			STATUS current
			DESCRIPTION
				"get the power of R4 in link16."
			::= { link16OBP 36 }		
		
--  1.3.6.1.4.1.47477.10.21.16.3.7
		-- 1.3.6.1.4.1.47477.10.21.16.3.7
		link16_R1Wave OBJECT-TYPE
			SYNTAX INTEGER
				{
				w1310nm(0),
				w1550nm(1),
				na(2)
				}
			MAX-ACCESS read-write
			STATUS current
			DESCRIPTION
				"get or set the wave length of R1 in link16."
			::= { link16OBP 7 }

		
--  1.3.6.1.4.1.47477.10.21.16.3.8
		-- 1.3.6.1.4.1.47477.10.21.16.3.8
		link16_R2Wave OBJECT-TYPE
			SYNTAX INTEGER
				{
				w1310nm(0),
				w1550nm(1),
				na(2)
				}
			MAX-ACCESS read-write
			STATUS current
			DESCRIPTION
				"get or set the wave length of R2 in link16."
			::= { link16OBP 8 }


--  1.3.6.1.4.1.47477.10.21.16.3.27
		-- 1.3.6.1.4.1.47477.10.21.16.3.27
		link16_R3Wave OBJECT-TYPE
			SYNTAX INTEGER
				{
				w1310nm(0),
				w1550nm(1),
				na(2)
				}
			MAX-ACCESS read-write
			STATUS current
			DESCRIPTION
				"get or set the wave length of R3 in link16."
			::= { link16OBP 27 }

		
--  1.3.6.1.4.1.47477.10.21.16.3.28
		-- 1.3.6.1.4.1.47477.10.21.16.3.28
		link16_R4Wave OBJECT-TYPE
			SYNTAX INTEGER
				{
				w1310nm(0),
				w1550nm(1),
				na(2)
				}
			MAX-ACCESS read-write
			STATUS current
			DESCRIPTION
				"get or set the wave length of R4 in link16."
			::= { link16OBP 28 }
			
--  1.3.6.1.4.1.47477.10.21.16.3.9
		-- 1.3.6.1.4.1.47477.10.21.16.3.9
		link16_R1AlarmPower OBJECT-TYPE
			SYNTAX DisplayString
			MAX-ACCESS read-write
			STATUS current
			DESCRIPTION
				"get or set the power alarm threshold of R1 in link16."
			::= { link16OBP 9 }

		
--  1.3.6.1.4.1.47477.10.21.16.3.10
		-- 1.3.6.1.4.1.47477.10.21.16.3.10
		link16_R2AlarmPower OBJECT-TYPE
			SYNTAX DisplayString
			MAX-ACCESS read-write
			STATUS current
			DESCRIPTION
				"get or set the power alarm threshold of R2 in link16."
			::= { link16OBP 10 }


--  1.3.6.1.4.1.47477.10.21.16.3.29
		-- 1.3.6.1.4.1.47477.10.21.16.3.29
		link16_R3AlarmPower OBJECT-TYPE
			SYNTAX DisplayString
			MAX-ACCESS read-write
			STATUS current
			DESCRIPTION
				"get or set the power alarm threshold of R3 in link16."
			::= { link16OBP 29 }

		
--  1.3.6.1.4.1.47477.10.21.16.3.30
		-- 1.3.6.1.4.1.47477.10.21.16.3.30
		link16_R4AlarmPower OBJECT-TYPE
			SYNTAX DisplayString
			MAX-ACCESS read-write
			STATUS current
			DESCRIPTION
				"get or set the power alarm threshold of R4 in link16."
			::= { link16OBP 30 }

-- OBP4
--  1.3.6.1.4.1.47477.10.21.16.3.37
		-- 1.3.6.1.4.1.47477.10.21.16.3.37
		link16_1R1Power OBJECT-TYPE
			SYNTAX DisplayString
			MAX-ACCESS read-only
			STATUS current
			DESCRIPTION
				"get the power of 1R1 in link16."
			::= { link16OBP 37 }
			
--  1.3.6.1.4.1.47477.10.21.16.3.38
		-- 1.3.6.1.4.1.47477.10.21.16.3.38
		link16_1R2Power OBJECT-TYPE
			SYNTAX DisplayString
			MAX-ACCESS read-only
			STATUS current
			DESCRIPTION
				"get the power of 1R2 in link16."
			::= { link16OBP 38 }

--  1.3.6.1.4.1.47477.10.21.16.3.39
		-- 1.3.6.1.4.1.47477.10.21.16.3.39
		link16_1R3Power OBJECT-TYPE
			SYNTAX DisplayString
			MAX-ACCESS read-only
			STATUS current
			DESCRIPTION
				"get the power of 1R3 in link16."
			::= { link16OBP 39 }
			
--  1.3.6.1.4.1.47477.10.21.16.3.40
		-- 1.3.6.1.4.1.47477.10.21.16.3.40
		link16_1R4Power OBJECT-TYPE
			SYNTAX DisplayString
			MAX-ACCESS read-only
			STATUS current
			DESCRIPTION
				"get the power of 1R4 in link16."
			::= { link16OBP 40 }

--  1.3.6.1.4.1.47477.10.21.16.3.41
		-- 1.3.6.1.4.1.47477.10.21.16.3.41
		link16_2R1Power OBJECT-TYPE
			SYNTAX DisplayString
			MAX-ACCESS read-only
			STATUS current
			DESCRIPTION
				"get the power of 2R1 in link16."
			::= { link16OBP 41 }
			
--  1.3.6.1.4.1.47477.10.21.16.3.42
		-- 1.3.6.1.4.1.47477.10.21.16.3.42
		link16_2R2Power OBJECT-TYPE
			SYNTAX DisplayString
			MAX-ACCESS read-only
			STATUS current
			DESCRIPTION
				"get the power of 2R2 in link16."
			::= { link16OBP 42 }

--  1.3.6.1.4.1.47477.10.21.16.3.41
		-- 1.3.6.1.4.1.47477.10.21.16.3.43
		link16_2R3Power OBJECT-TYPE
			SYNTAX DisplayString
			MAX-ACCESS read-only
			STATUS current
			DESCRIPTION
				"get the power of 2R3 in link16."
			::= { link16OBP 43 }
			
--  1.3.6.1.4.1.47477.10.21.16.3.42
		-- 1.3.6.1.4.1.47477.10.21.16.3.44
		link16_2R4Power OBJECT-TYPE
			SYNTAX DisplayString
			MAX-ACCESS read-only
			STATUS current
			DESCRIPTION
				"get the power of 2R4 in link16."
			::= { link16OBP 44 }
			
--  1.3.6.1.4.1.47477.10.21.16.3.49
		-- 1.3.6.1.4.1.47477.10.21.16.3.49
		link16_1R1Wave OBJECT-TYPE
			SYNTAX INTEGER
				{
				w850nm(0),
				na(2)
				}
			MAX-ACCESS read-only
			STATUS current
			DESCRIPTION
				"get the wave length of 1R1 in link16."
			::= { link16OBP 49 }
		
--  1.3.6.1.4.1.47477.10.21.16.3.60
		-- 1.3.6.1.4.1.47477.10.21.16.3.60
		link16_1R2Wave OBJECT-TYPE
			SYNTAX INTEGER
				{
				w850nm(0),
				na(2)
				}
			MAX-ACCESS read-only
			STATUS current
			DESCRIPTION
				"get the wave length of 1R2 in link16."
			::= { link16OBP 60 }

--  1.3.6.1.4.1.47477.10.21.16.3.61
		-- 1.3.6.1.4.1.47477.10.21.16.3.61
		link16_1R3Wave OBJECT-TYPE
			SYNTAX INTEGER
				{
				w850nm(0),
				na(2)
				}
			MAX-ACCESS read-only
			STATUS current
			DESCRIPTION
				"get the wave length of 1R3 in link16."
			::= { link16OBP 61 }

		
--  1.3.6.1.4.1.47477.10.21.16.3.62
		-- 1.3.6.1.4.1.47477.10.21.16.3.62
		link16_1R4Wave OBJECT-TYPE
			SYNTAX INTEGER
				{
				w850nm(0),
				na(2)
				}
			MAX-ACCESS read-only
			STATUS current
			DESCRIPTION
				"get the wave length of 1R4 in link16."
			::= { link16OBP 62 }
	
--  1.3.6.1.4.1.47477.10.21.16.3.63
		-- 1.3.6.1.4.1.47477.10.21.16.3.63
		link16_2R1Wave OBJECT-TYPE
			SYNTAX INTEGER
				{
				w850nm(0),
				na(2)
				}
			MAX-ACCESS read-only
			STATUS current
			DESCRIPTION
				"get the wave length of 2R1 in link16."
			::= { link16OBP 63 }

		
--  1.3.6.1.4.1.47477.10.21.16.3.64
		-- 1.3.6.1.4.1.47477.10.21.16.3.64
		link16_2R2Wave OBJECT-TYPE
			SYNTAX INTEGER
				{
				w850nm(0),
				na(2)
				}
			MAX-ACCESS read-only
			STATUS current
			DESCRIPTION
				"get the wave length of 2R2 in link16."
			::= { link16OBP 64 }	
	
--  1.3.6.1.4.1.47477.10.21.16.3.65
		-- 1.3.6.1.4.1.47477.10.21.16.3.65
		link16_2R3Wave OBJECT-TYPE
			SYNTAX INTEGER
				{
				w850nm(0),
				na(2)
				}
			MAX-ACCESS read-only
			STATUS current
			DESCRIPTION
				"get the wave length of 2R3 in link16."
			::= { link16OBP 65 }

		
--  1.3.6.1.4.1.47477.10.21.16.3.66
		-- 1.3.6.1.4.1.47477.10.21.16.3.66
		link16_2R4Wave OBJECT-TYPE
			SYNTAX INTEGER
				{
				w850nm(0),
				na(2)
				}
			MAX-ACCESS read-only
			STATUS current
			DESCRIPTION
				"get the wave length of 2R4 in link16."
			::= { link16OBP 66 }	
			
--  1.3.6.1.4.1.47477.10.21.16.3.31
		-- 1.3.6.1.4.1.47477.10.21.16.3.31
		link16_1R1AlarmPower OBJECT-TYPE
			SYNTAX DisplayString
			MAX-ACCESS read-write
			STATUS current
			DESCRIPTION
				"get or set the power alarm threshold of 1R1 in link16."
			::= { link16OBP 31 }
			
--  1.3.6.1.4.1.47477.10.21.16.3.32
		-- 1.3.6.1.4.1.47477.10.21.16.3.32
		link16_1R2AlarmPower OBJECT-TYPE
			SYNTAX DisplayString
			MAX-ACCESS read-write
			STATUS current
			DESCRIPTION
				"get or set the power alarm threshold of 1R2 in link16."
			::= { link16OBP 32 }

--  1.3.6.1.4.1.47477.10.21.16.3.33
		-- 1.3.6.1.4.1.47477.10.21.16.3.33
		link16_1R3AlarmPower OBJECT-TYPE
			SYNTAX DisplayString
			MAX-ACCESS read-write
			STATUS current
			DESCRIPTION
				"get or set the power alarm threshold of 1R3 in link16."
			::= { link16OBP 33 }
			
--  1.3.6.1.4.1.47477.10.21.16.3.34
		-- 1.3.6.1.4.1.47477.10.21.16.3.34
		link16_1R4AlarmPower OBJECT-TYPE
			SYNTAX DisplayString
			MAX-ACCESS read-write
			STATUS current
			DESCRIPTION
				"get or set the power alarm threshold of 1R4 in link16."
			::= { link16OBP 34 }

--  1.3.6.1.4.1.47477.10.21.16.3.45
		-- 1.3.6.1.4.1.47477.10.21.16.3.45
		link16_2R1AlarmPower OBJECT-TYPE
			SYNTAX DisplayString
			MAX-ACCESS read-write
			STATUS current
			DESCRIPTION
				"get or set the power alarm threshold of 2R1 in link16."
			::= { link16OBP 45 }
			
--  1.3.6.1.4.1.47477.10.21.16.3.46
		-- 1.3.6.1.4.1.47477.10.21.16.3.46
		link16_2R2AlarmPower OBJECT-TYPE
			SYNTAX DisplayString
			MAX-ACCESS read-write
			STATUS current
			DESCRIPTION
				"get or set the power alarm threshold of 2R2 in link16."
			::= { link16OBP 46 }

--  1.3.6.1.4.1.47477.10.21.16.3.47
		-- 1.3.6.1.4.1.47477.10.21.16.3.47
		link16_2R3AlarmPower OBJECT-TYPE
			SYNTAX DisplayString
			MAX-ACCESS read-write
			STATUS current
			DESCRIPTION
				"get or set the power alarm threshold of 2R3 in link16."
			::= { link16OBP 47 }
			
--  1.3.6.1.4.1.47477.10.21.16.3.48
		-- 1.3.6.1.4.1.47477.10.21.16.3.48
		link16_2R4AlarmPower OBJECT-TYPE
			SYNTAX DisplayString
			MAX-ACCESS read-write
			STATUS current
			DESCRIPTION
				"get or set the power alarm threshold of 2R4 in link16."
			::= { link16OBP 48 }
			
--  1.3.6.1.4.1.47477.10.21.16.3.11
		-- 1.3.6.1.4.1.47477.10.21.16.3.11
		link16_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link16OBP 11 }
			
--  1.3.6.1.4.1.47477.10.21.16.3.67
		-- 1.3.6.1.4.1.47477.10.21.16.3.67
		link16_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link16OBP 67 }
			
--  1.3.6.1.4.1.47477.10.21.16.3.68
		-- 1.3.6.1.4.1.47477.10.21.16.3.68
		link16_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link16OBP 68 }
			
--  1.3.6.1.4.1.47477.10.21.16.3.12
		-- 1.3.6.1.4.1.47477.10.21.16.3.12
		link16_ReturnDelay OBJECT-TYPE
			--SYNTAX Integer32
			SYNTAX Integer32
			MAX-ACCESS read-write
			STATUS current
			DESCRIPTION
				"get or set how long link16 takes to return to automatic mode."
			::= { link16OBP 12 }
			
--  1.3.6.1.4.1.47477.10.21.16.3.13
		-- 1.3.6.1.4.1.47477.10.21.16.3.13
		link16_BackMode OBJECT-TYPE
			SYNTAX INTEGER
				{
				autoNoBack(0),
				autoBack(1)
				}
			MAX-ACCESS read-write
			STATUS current
			DESCRIPTION
				"get or set the back mode of link16."
			::= { link16OBP 13 }

		
--  1.3.6.1.4.1.47477.10.21.16.3.14
		-- 1.3.6.1.4.1.47477.10.21.16.3.14
		link16_BackDelay OBJECT-TYPE
			SYNTAX Integer32
			MAX-ACCESS read-write
			STATUS current
			DESCRIPTION
				"get or set the back delay."
			::= { link16OBP 14 }

--  1.3.6.1.4.1.47477.10.21.16.3.15
		-- 1.3.6.1.4.1.47477.10.21.16.3.15
		link16_ActiveHeartSwitch OBJECT-TYPE
			SYNTAX INTEGER
				{
				off(0),
				on(1)
				}
			MAX-ACCESS read-write
			STATUS current
			DESCRIPTION
				"get or set the switch status of active heartbeat."
			::= { link16OBP 15 }

		
--  1.3.6.1.4.1.47477.10.21.16.3.16
		-- 1.3.6.1.4.1.47477.10.21.16.3.16
		link16_ActiveSendInterval OBJECT-TYPE
			SYNTAX Integer32
			MAX-ACCESS read-write
			STATUS current
			DESCRIPTION
				"get or set the send interval of active heartbeat."
			::= { link16OBP 16 }		

--  1.3.6.1.4.1.47477.10.21.16.3.17
		-- 1.3.6.1.4.1.47477.10.21.16.3.17
		link16_ActiveTimeOut OBJECT-TYPE
			SYNTAX Integer32
			MAX-ACCESS read-write
			STATUS current
			DESCRIPTION
				"get or set how long the active heartbeat send timeout."
			::= { link16OBP 17 }

--  1.3.6.1.4.1.47477.10.21.16.3.18
		-- 1.3.6.1.4.1.47477.10.21.16.3.18
		link16_ActiveLossBypass OBJECT-TYPE
			SYNTAX Integer32
			MAX-ACCESS read-write
			STATUS current
			DESCRIPTION
				"get or set the bypass for active heartbeat packet loss."
			::= { link16OBP 18 }

--  1.3.6.1.4.1.47477.10.21.16.3.19
		-- 1.3.6.1.4.1.47477.10.21.16.3.19
		link16_PingIpAddress OBJECT-TYPE
			SYNTAX IpAddress
			MAX-ACCESS read-write
			STATUS current
			DESCRIPTION
				"get or set the ping ip address of link16."
			::= { link16OBP 19 }

--  1.3.6.1.4.1.47477.10.21.16.3.20
		-- 1.3.6.1.4.1.47477.10.21.16.3.20
		link16_PassiveHeartSwitch OBJECT-TYPE
			SYNTAX INTEGER
				{
				off(0),
				on(1)
				}
			MAX-ACCESS read-write
			STATUS current
			DESCRIPTION
				"get or set the switch status of passive heartbeat."
			::= { link16OBP 20 }
	

--  1.3.6.1.4.1.47477.10.21.16.3.21
		-- 1.3.6.1.4.1.47477.10.21.16.3.21
		link16_PassiveTimeOut OBJECT-TYPE
			SYNTAX Integer32
			MAX-ACCESS read-write
			STATUS current
			DESCRIPTION
				"get or set how long the passive heartbeat send timeout."
			::= { link16OBP 21 }

--  1.3.6.1.4.1.47477.10.21.16.3.22
		-- 1.3.6.1.4.1.47477.10.21.16.3.22
		link16_PassiveLossBypass OBJECT-TYPE
			SYNTAX Integer32
			MAX-ACCESS read-write
			STATUS current
			DESCRIPTION
				"get or set the bypass for passive heartbeat packet loss."
			::= { link16OBP 22 }

--  1.3.6.1.4.1.47477.10.21.16.3.23
		-- 1.3.6.1.4.1.47477.10.21.16.3.23
		link16_SwitchProtect OBJECT-TYPE
			SYNTAX INTEGER
				{
				off(0),
				on(1)
				}
			MAX-ACCESS read-write
			STATUS current
			DESCRIPTION
				"get or set the switch protection status of link16."
			::= { link16OBP 23 }
			
--  1.3.6.1.4.1.47477.10.21.16.3.24
		-- 1.3.6.1.4.1.47477.10.21.16.3.24
		link16_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link16OBP 24 }		

--  1.3.6.1.4.1.47477.10.21.16.3.25
		-- 1.3.6.1.4.1.47477.10.21.16.3.25
		link16_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link16OBP 25 }	

--  1.3.6.1.4.1.47477.10.21.16.3.26
		-- 1.3.6.1.4.1.47477.10.21.16.3.26
		link16_PowerAlarmStatus OBJECT-TYPE
			SYNTAX INTEGER
				{
				off(0),
				alarm(1),
				normal(2),
				na(3)
				}
			MAX-ACCESS read-only
			STATUS current
			DESCRIPTION
				"get whether a power alarm is generated."
			::= { link16OBP 26 }	


-- 1.3.6.1.4.1.47477.10.21.16.3.50.1
	link16_WorkModeChange 	OBJECT-TYPE    
    SYNTAX INTEGER	{
				manualMode(0),
				autoMode(1)
		}
	MAX-ACCESS read-only
	STATUS current
    DESCRIPTION
        "The Link mode Changed."
    ::= {link16OBPTrap 1}

-- 1.3.6.1.4.1.47477.10.21.16.3.50.2
	link16_StateChange 	OBJECT-TYPE    
    SYNTAX INTEGER	{
				bypass(0),
				primary(1)
		}
	MAX-ACCESS read-only
	STATUS current
    DESCRIPTION
        "The Link State(Channel) Changed."
    ::= {link16OBPTrap 2}

-- 1.3.6.1.4.1.47477.10.21.16.3.50.3
	link16_R1WaveSet 	OBJECT-TYPE    
    SYNTAX INTEGER	{
				w1310nm(0),
				w1550nm(1)
		}
	MAX-ACCESS read-only
	STATUS current
    DESCRIPTION
        "Set The link16 R1 Wave."
    ::= {link16OBPTrap 3}

-- 1.3.6.1.4.1.47477.10.21.16.3.50.4
	link16_R2WaveSet 	OBJECT-TYPE    
    SYNTAX INTEGER	{
				w1310nm(0),
				w1550nm(1)
		}
	MAX-ACCESS read-only
	STATUS current
    DESCRIPTION
        "Set The link16 R2 Wave."
    ::= {link16OBPTrap 4}			

-- 1.3.6.1.4.1.47477.10.21.16.3.50.5
	link16_R3WaveSet 	OBJECT-TYPE    
    SYNTAX INTEGER	{
				w1310nm(0),
				w1550nm(1)
		}
	MAX-ACCESS read-only
	STATUS current
    DESCRIPTION
        "Set The link16 R3 Wave."
    ::= {link16OBPTrap 5}

-- 1.3.6.1.4.1.47477.10.21.16.3.50.6
	link16_R4WaveSet 	OBJECT-TYPE    
    SYNTAX INTEGER	{
				w1310nm(0),
				w1550nm(1)
		}
	MAX-ACCESS read-only
	STATUS current
    DESCRIPTION
        "Set The link16 R4 Wave."
    ::= {link16OBPTrap 6}	
	
-- 1.3.6.1.4.1.47477.10.21.16.3.50.7
	link16_R1AlarmSet 	OBJECT-TYPE    
    SYNTAX DisplayString
	MAX-ACCESS read-only
	STATUS current
    DESCRIPTION
        "Set The link16 R1 Alarm Threshold."
    ::= {link16OBPTrap 7}

-- 1.3.6.1.4.1.47477.10.21.16.3.50.8
	link16_R2AlarmSet 	OBJECT-TYPE    
    SYNTAX DisplayString
	MAX-ACCESS read-only
	STATUS current
    DESCRIPTION
        "Set The link16 R2 Alarm Threshold."
    ::= {link16OBPTrap 8}
	
-- 1.3.6.1.4.1.47477.10.21.16.3.50.9
	link16_R3AlarmSet 	OBJECT-TYPE    
    SYNTAX DisplayString
	MAX-ACCESS read-only
	STATUS current
    DESCRIPTION
        "Set The link16 R3 Alarm Threshold."
    ::= {link16OBPTrap 9}

-- 1.3.6.1.4.1.47477.10.21.16.3.50.10
	link16_R4AlarmSet 	OBJECT-TYPE    
    SYNTAX DisplayString
	MAX-ACCESS read-only
	STATUS current
    DESCRIPTION
        "Set The link16 R4 Alarm Threshold."
    ::= {link16OBPTrap 10}	
	
	
-- 1.3.6.1.4.1.47477.10.21.16.3.50.11
	link16_1R1AlarmSet 	OBJECT-TYPE    
    SYNTAX DisplayString
	MAX-ACCESS read-only
	STATUS current
    DESCRIPTION
        "Set The link16 1R1 Alarm Threshold."
    ::= {link16OBPTrap 11}

-- 1.3.6.1.4.1.47477.10.21.16.3.50.12
	link16_2R1AlarmSet 	OBJECT-TYPE    
    SYNTAX DisplayString
	MAX-ACCESS read-only
	STATUS current
    DESCRIPTION
        "Set The link16 2R1 Alarm Threshold."
    ::= {link16OBPTrap 12}
	
-- 1.3.6.1.4.1.47477.10.21.16.3.50.13
	link16_1R2AlarmSet 	OBJECT-TYPE    
    SYNTAX DisplayString
	MAX-ACCESS read-only
	STATUS current
    DESCRIPTION
        "Set The link16 1R2 Alarm Threshold."
    ::= {link16OBPTrap 13}

-- 1.3.6.1.4.1.47477.10.21.16.3.50.14
	link16_2R2AlarmSet 	OBJECT-TYPE    
    SYNTAX DisplayString
	MAX-ACCESS read-only
	STATUS current
    DESCRIPTION
        "Set The link16 2R2 Alarm Threshold."
    ::= {link16OBPTrap 14}
	
-- 1.3.6.1.4.1.47477.10.21.16.3.50.15
	link16_1R3AlarmSet 	OBJECT-TYPE    
    SYNTAX DisplayString
	MAX-ACCESS read-only
	STATUS current
    DESCRIPTION
        "Set The link16 1R3 Alarm Threshold."
    ::= {link16OBPTrap 15}

-- 1.3.6.1.4.1.47477.10.21.16.3.50.16
	link16_2R3AlarmSet 	OBJECT-TYPE    
    SYNTAX DisplayString
	MAX-ACCESS read-only
	STATUS current
    DESCRIPTION
        "Set The link16 2R3 Alarm Threshold."
    ::= {link16OBPTrap 16}
	
-- 1.3.6.1.4.1.47477.10.21.16.3.50.17
	link16_1R4AlarmSet 	OBJECT-TYPE    
    SYNTAX DisplayString
	MAX-ACCESS read-only
	STATUS current
    DESCRIPTION
        "Set The link16 1R4 Alarm Threshold."
    ::= {link16OBPTrap 17}

-- 1.3.6.1.4.1.47477.10.21.16.3.50.18
	link16_2R4AlarmSet 	OBJECT-TYPE    
    SYNTAX DisplayString
	MAX-ACCESS read-only
	STATUS current
    DESCRIPTION
        "Set The link16 2R4 Alarm Threshold."
    ::= {link16OBPTrap 18}
	
-- 1.3.6.1.4.1.47477.10.21.16.3.50.19
	link16_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link16 PowerAlarmBypass2 Changed."
    ::= {link16OBPTrap 19}
	
-- 1.3.6.1.4.1.47477.10.21.16.3.50.20
	link16_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link16 PowerAlarmBypass4 Changed."
    ::= {link16OBPTrap 20}	
	
-- 1.3.6.1.4.1.47477.10.21.16.3.50.21
	link16_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link16 PowerAlarmBypass8 Changed."
    ::= {link16OBPTrap 21}
	
-- 1.3.6.1.4.1.47477.10.21.16.3.50.22
	link16_powerAlarmR1 	OBJECT-TYPE    
    SYNTAX DisplayString
	MAX-ACCESS read-only
	STATUS current
    DESCRIPTION
        "Set The link16 R1 Power Status Alarm."
    ::= {link16OBPTrap 22}
	
-- 1.3.6.1.4.1.47477.10.21.16.3.50.23
	link16_powerAlarmR2 	OBJECT-TYPE    
    SYNTAX DisplayString
	MAX-ACCESS read-only
	STATUS current
    DESCRIPTION
        "Set The link16 R2 Power Status Alarm."
    ::= {link16OBPTrap 23}
	
-- 1.3.6.1.4.1.47477.10.21.16.3.50.24
	link16_powerAlarmR3 	OBJECT-TYPE    
    SYNTAX DisplayString
	MAX-ACCESS read-only
	STATUS current
    DESCRIPTION
        "Set The link16 R3 Power Status Alarm."
    ::= {link16OBPTrap 24}
	
-- 1.3.6.1.4.1.47477.10.21.16.3.50.25
	link16_powerAlarmR4 	OBJECT-TYPE    
    SYNTAX DisplayString
	MAX-ACCESS read-only
	STATUS current
    DESCRIPTION
        "Set The link16 R4 Power Status Alarm."
    ::= {link16OBPTrap 25}
	
	
-- 1.3.6.1.4.1.47477.10.21.16.3.50.26
	link16_powerAlarm1R1 	OBJECT-TYPE    
    SYNTAX DisplayString
	MAX-ACCESS read-only
	STATUS current
    DESCRIPTION
        "Set The link16 1R1 Power Status Alarm."
    ::= {link16OBPTrap 26}
	
-- 1.3.6.1.4.1.47477.10.21.16.3.50.27
	link16_powerAlarm2R1 	OBJECT-TYPE    
    SYNTAX DisplayString
	MAX-ACCESS read-only
	STATUS current
    DESCRIPTION
        "Set The link16 2R1 Power Status Alarm."
    ::= {link16OBPTrap 27}
	
-- 1.3.6.1.4.1.47477.10.21.16.3.50.28
	link16_powerAlarm1R2 	OBJECT-TYPE    
    SYNTAX DisplayString
	MAX-ACCESS read-only
	STATUS current
    DESCRIPTION
        "Set The link16 1R2 Power Status Alarm."
    ::= {link16OBPTrap 28}
	
-- 1.3.6.1.4.1.47477.10.21.16.3.50.29
	link16_powerAlarm2R2 	OBJECT-TYPE    
    SYNTAX DisplayString
	MAX-ACCESS read-only
	STATUS current
    DESCRIPTION
        "Set The link16 2R2 Power Status Alarm."
    ::= {link16OBPTrap 29}
	
-- 1.3.6.1.4.1.47477.10.21.16.3.50.30
	link16_powerAlarm1R3 	OBJECT-TYPE    
    SYNTAX DisplayString
	MAX-ACCESS read-only
	STATUS current
    DESCRIPTION
        "Set The link16 1R3 Power Status Alarm."
    ::= {link16OBPTrap 30}
	
-- 1.3.6.1.4.1.47477.10.21.16.3.50.31
	link16_powerAlarm2R3 	OBJECT-TYPE    
    SYNTAX DisplayString
	MAX-ACCESS read-only
	STATUS current
    DESCRIPTION
        "Set The link16 2R1 Power Status Alarm."
    ::= {link16OBPTrap 31}
	
-- 1.3.6.1.4.1.47477.10.21.16.3.50.32
	link16_powerAlarm1R4 	OBJECT-TYPE    
    SYNTAX DisplayString
	MAX-ACCESS read-only
	STATUS current
    DESCRIPTION
        "Set The link16 1R4 Power Status Alarm."
    ::= {link16OBPTrap 32}
	
-- 1.3.6.1.4.1.47477.10.21.16.3.50.33
	link16_powerAlarm2R4 	OBJECT-TYPE    
    SYNTAX DisplayString
	MAX-ACCESS read-only
	STATUS current
    DESCRIPTION
        "Set The link16 2R4 Power Status Alarm."
    ::= {link16OBPTrap 33}
	
--  1.3.6.1.4.1.47477.10.21.17.3.1
		-- 1.3.6.1.4.1.47477.10.21.17.3.1
		link17_State OBJECT-TYPE
			SYNTAX INTEGER
				{
				off(0),
				on(1)
				}
			MAX-ACCESS read-only
			STATUS current
			DESCRIPTION
				"get the information about whether link17 is working."
			::= { link17OBP 1 }

		
--  1.3.6.1.4.1.47477.10.21.17.3.2
		-- 1.3.6.1.4.1.47477.10.21.17.3.2
		link17_DeviceType OBJECT-TYPE
			SYNTAX DisplayString
			MAX-ACCESS read-only
			STATUS current
			DESCRIPTION
				"get the type of card in link17."
			::= { link17OBP 2 }

			
--  1.3.6.1.4.1.47477.10.21.17.3.3
		-- 1.3.6.1.4.1.47477.10.21.17.3.3
		link17_WorkMode OBJECT-TYPE
			SYNTAX INTEGER
				{
				manualMode(0),
				autoMode(1)
				}
			MAX-ACCESS read-write
			STATUS current
			DESCRIPTION
				"get or set link17's work mode."
			::= { link17OBP 3 }

		
--  1.3.6.1.4.1.47477.10.21.17.3.4
		-- 1.3.6.1.4.1.47477.10.21.17.3.4
		link17_Channel OBJECT-TYPE
			SYNTAX INTEGER
				{
				bypass(0),
				primary(1)
				}
			MAX-ACCESS read-write
			STATUS current
			DESCRIPTION
				"get or set the channel in which link17 works."
			::= { link17OBP 4 }


--  1.3.6.1.4.1.47477.10.21.17.3.5
		-- 1.3.6.1.4.1.47477.10.21.17.3.5
		link17_R1Power OBJECT-TYPE
			SYNTAX DisplayString
			MAX-ACCESS read-only
			STATUS current
			DESCRIPTION
				"get the power of R1 in link17."
			::= { link17OBP 5 }

		
--  1.3.6.1.4.1.47477.10.21.17.3.6
		-- 1.3.6.1.4.1.47477.10.21.17.3.6
		link17_R2Power OBJECT-TYPE
			SYNTAX DisplayString
			MAX-ACCESS read-only
			STATUS current
			DESCRIPTION
				"get the power of R2 in link17."
			::= { link17OBP 6 }
			
--  1.3.6.1.4.1.47477.10.21.17.3.35
		-- 1.3.6.1.4.1.47477.10.21.17.3.35
		link17_R3Power OBJECT-TYPE
			SYNTAX DisplayString
			MAX-ACCESS read-only
			STATUS current
			DESCRIPTION
				"get the power of R3 in link17."
			::= { link17OBP 35 }
			
--  1.3.6.1.4.1.47477.10.21.17.3.36
		-- 1.3.6.1.4.1.47477.10.21.17.3.36
		link17_R4Power OBJECT-TYPE
			SYNTAX DisplayString
			MAX-ACCESS read-only
			STATUS current
			DESCRIPTION
				"get the power of R4 in link17."
			::= { link17OBP 36 }		
		
--  1.3.6.1.4.1.47477.10.21.17.3.7
		-- 1.3.6.1.4.1.47477.10.21.17.3.7
		link17_R1Wave OBJECT-TYPE
			SYNTAX INTEGER
				{
				w1310nm(0),
				w1550nm(1),
				na(2)
				}
			MAX-ACCESS read-write
			STATUS current
			DESCRIPTION
				"get or set the wave length of R1 in link17."
			::= { link17OBP 7 }

		
--  1.3.6.1.4.1.47477.10.21.17.3.8
		-- 1.3.6.1.4.1.47477.10.21.17.3.8
		link17_R2Wave OBJECT-TYPE
			SYNTAX INTEGER
				{
				w1310nm(0),
				w1550nm(1),
				na(2)
				}
			MAX-ACCESS read-write
			STATUS current
			DESCRIPTION
				"get or set the wave length of R2 in link17."
			::= { link17OBP 8 }


--  1.3.6.1.4.1.47477.10.21.17.3.27
		-- 1.3.6.1.4.1.47477.10.21.17.3.27
		link17_R3Wave OBJECT-TYPE
			SYNTAX INTEGER
				{
				w1310nm(0),
				w1550nm(1),
				na(2)
				}
			MAX-ACCESS read-write
			STATUS current
			DESCRIPTION
				"get or set the wave length of R3 in link17."
			::= { link17OBP 27 }

		
--  1.3.6.1.4.1.47477.10.21.17.3.28
		-- 1.3.6.1.4.1.47477.10.21.17.3.28
		link17_R4Wave OBJECT-TYPE
			SYNTAX INTEGER
				{
				w1310nm(0),
				w1550nm(1),
				na(2)
				}
			MAX-ACCESS read-write
			STATUS current
			DESCRIPTION
				"get or set the wave length of R4 in link17."
			::= { link17OBP 28 }
			
--  1.3.6.1.4.1.47477.10.21.17.3.9
		-- 1.3.6.1.4.1.47477.10.21.17.3.9
		link17_R1AlarmPower OBJECT-TYPE
			SYNTAX DisplayString
			MAX-ACCESS read-write
			STATUS current
			DESCRIPTION
				"get or set the power alarm threshold of R1 in link17."
			::= { link17OBP 9 }

		
--  1.3.6.1.4.1.47477.10.21.17.3.10
		-- 1.3.6.1.4.1.47477.10.21.17.3.10
		link17_R2AlarmPower OBJECT-TYPE
			SYNTAX DisplayString
			MAX-ACCESS read-write
			STATUS current
			DESCRIPTION
				"get or set the power alarm threshold of R2 in link17."
			::= { link17OBP 10 }


--  1.3.6.1.4.1.47477.10.21.17.3.29
		-- 1.3.6.1.4.1.47477.10.21.17.3.29
		link17_R3AlarmPower OBJECT-TYPE
			SYNTAX DisplayString
			MAX-ACCESS read-write
			STATUS current
			DESCRIPTION
				"get or set the power alarm threshold of R3 in link17."
			::= { link17OBP 29 }

		
--  1.3.6.1.4.1.47477.10.21.17.3.30
		-- 1.3.6.1.4.1.47477.10.21.17.3.30
		link17_R4AlarmPower OBJECT-TYPE
			SYNTAX DisplayString
			MAX-ACCESS read-write
			STATUS current
			DESCRIPTION
				"get or set the power alarm threshold of R4 in link17."
			::= { link17OBP 30 }

-- OBP4
--  1.3.6.1.4.1.47477.10.21.17.3.37
		-- 1.3.6.1.4.1.47477.10.21.17.3.37
		link17_1R1Power OBJECT-TYPE
			SYNTAX DisplayString
			MAX-ACCESS read-only
			STATUS current
			DESCRIPTION
				"get the power of 1R1 in link17."
			::= { link17OBP 37 }
			
--  1.3.6.1.4.1.47477.10.21.17.3.38
		-- 1.3.6.1.4.1.47477.10.21.17.3.38
		link17_1R2Power OBJECT-TYPE
			SYNTAX DisplayString
			MAX-ACCESS read-only
			STATUS current
			DESCRIPTION
				"get the power of 1R2 in link17."
			::= { link17OBP 38 }

--  1.3.6.1.4.1.47477.10.21.17.3.39
		-- 1.3.6.1.4.1.47477.10.21.17.3.39
		link17_1R3Power OBJECT-TYPE
			SYNTAX DisplayString
			MAX-ACCESS read-only
			STATUS current
			DESCRIPTION
				"get the power of 1R3 in link17."
			::= { link17OBP 39 }
			
--  1.3.6.1.4.1.47477.10.21.17.3.40
		-- 1.3.6.1.4.1.47477.10.21.17.3.40
		link17_1R4Power OBJECT-TYPE
			SYNTAX DisplayString
			MAX-ACCESS read-only
			STATUS current
			DESCRIPTION
				"get the power of 1R4 in link17."
			::= { link17OBP 40 }

--  1.3.6.1.4.1.47477.10.21.17.3.41
		-- 1.3.6.1.4.1.47477.10.21.17.3.41
		link17_2R1Power OBJECT-TYPE
			SYNTAX DisplayString
			MAX-ACCESS read-only
			STATUS current
			DESCRIPTION
				"get the power of 2R1 in link17."
			::= { link17OBP 41 }
			
--  1.3.6.1.4.1.47477.10.21.17.3.42
		-- 1.3.6.1.4.1.47477.10.21.17.3.42
		link17_2R2Power OBJECT-TYPE
			SYNTAX DisplayString
			MAX-ACCESS read-only
			STATUS current
			DESCRIPTION
				"get the power of 2R2 in link17."
			::= { link17OBP 42 }

--  1.3.6.1.4.1.47477.10.21.17.3.41
		-- 1.3.6.1.4.1.47477.10.21.17.3.43
		link17_2R3Power OBJECT-TYPE
			SYNTAX DisplayString
			MAX-ACCESS read-only
			STATUS current
			DESCRIPTION
				"get the power of 2R3 in link17."
			::= { link17OBP 43 }
			
--  1.3.6.1.4.1.47477.10.21.17.3.42
		-- 1.3.6.1.4.1.47477.10.21.17.3.44
		link17_2R4Power OBJECT-TYPE
			SYNTAX DisplayString
			MAX-ACCESS read-only
			STATUS current
			DESCRIPTION
				"get the power of 2R4 in link17."
			::= { link17OBP 44 }
			
--  1.3.6.1.4.1.47477.10.21.17.3.49
		-- 1.3.6.1.4.1.47477.10.21.17.3.49
		link17_1R1Wave OBJECT-TYPE
			SYNTAX INTEGER
				{
				w850nm(0),
				na(2)
				}
			MAX-ACCESS read-only
			STATUS current
			DESCRIPTION
				"get the wave length of 1R1 in link17."
			::= { link17OBP 49 }
		
--  1.3.6.1.4.1.47477.10.21.17.3.60
		-- 1.3.6.1.4.1.47477.10.21.17.3.60
		link17_1R2Wave OBJECT-TYPE
			SYNTAX INTEGER
				{
				w850nm(0),
				na(2)
				}
			MAX-ACCESS read-only
			STATUS current
			DESCRIPTION
				"get the wave length of 1R2 in link17."
			::= { link17OBP 60 }

--  1.3.6.1.4.1.47477.10.21.17.3.61
		-- 1.3.6.1.4.1.47477.10.21.17.3.61
		link17_1R3Wave OBJECT-TYPE
			SYNTAX INTEGER
				{
				w850nm(0),
				na(2)
				}
			MAX-ACCESS read-only
			STATUS current
			DESCRIPTION
				"get the wave length of 1R3 in link17."
			::= { link17OBP 61 }

		
--  1.3.6.1.4.1.47477.10.21.17.3.62
		-- 1.3.6.1.4.1.47477.10.21.17.3.62
		link17_1R4Wave OBJECT-TYPE
			SYNTAX INTEGER
				{
				w850nm(0),
				na(2)
				}
			MAX-ACCESS read-only
			STATUS current
			DESCRIPTION
				"get the wave length of 1R4 in link17."
			::= { link17OBP 62 }
	
--  1.3.6.1.4.1.47477.10.21.17.3.63
		-- 1.3.6.1.4.1.47477.10.21.17.3.63
		link17_2R1Wave OBJECT-TYPE
			SYNTAX INTEGER
				{
				w850nm(0),
				na(2)
				}
			MAX-ACCESS read-only
			STATUS current
			DESCRIPTION
				"get the wave length of 2R1 in link17."
			::= { link17OBP 63 }

		
--  1.3.6.1.4.1.47477.10.21.17.3.64
		-- 1.3.6.1.4.1.47477.10.21.17.3.64
		link17_2R2Wave OBJECT-TYPE
			SYNTAX INTEGER
				{
				w850nm(0),
				na(2)
				}
			MAX-ACCESS read-only
			STATUS current
			DESCRIPTION
				"get the wave length of 2R2 in link17."
			::= { link17OBP 64 }	
	
--  1.3.6.1.4.1.47477.10.21.17.3.65
		-- 1.3.6.1.4.1.47477.10.21.17.3.65
		link17_2R3Wave OBJECT-TYPE
			SYNTAX INTEGER
				{
				w850nm(0),
				na(2)
				}
			MAX-ACCESS read-only
			STATUS current
			DESCRIPTION
				"get the wave length of 2R3 in link17."
			::= { link17OBP 65 }

		
--  1.3.6.1.4.1.47477.10.21.17.3.66
		-- 1.3.6.1.4.1.47477.10.21.17.3.66
		link17_2R4Wave OBJECT-TYPE
			SYNTAX INTEGER
				{
				w850nm(0),
				na(2)
				}
			MAX-ACCESS read-only
			STATUS current
			DESCRIPTION
				"get the wave length of 2R4 in link17."
			::= { link17OBP 66 }	
			
--  1.3.6.1.4.1.47477.10.21.17.3.31
		-- 1.3.6.1.4.1.47477.10.21.17.3.31
		link17_1R1AlarmPower OBJECT-TYPE
			SYNTAX DisplayString
			MAX-ACCESS read-write
			STATUS current
			DESCRIPTION
				"get or set the power alarm threshold of 1R1 in link17."
			::= { link17OBP 31 }
			
--  1.3.6.1.4.1.47477.10.21.17.3.32
		-- 1.3.6.1.4.1.47477.10.21.17.3.32
		link17_1R2AlarmPower OBJECT-TYPE
			SYNTAX DisplayString
			MAX-ACCESS read-write
			STATUS current
			DESCRIPTION
				"get or set the power alarm threshold of 1R2 in link17."
			::= { link17OBP 32 }

--  1.3.6.1.4.1.47477.10.21.17.3.33
		-- 1.3.6.1.4.1.47477.10.21.17.3.33
		link17_1R3AlarmPower OBJECT-TYPE
			SYNTAX DisplayString
			MAX-ACCESS read-write
			STATUS current
			DESCRIPTION
				"get or set the power alarm threshold of 1R3 in link17."
			::= { link17OBP 33 }
			
--  1.3.6.1.4.1.47477.10.21.17.3.34
		-- 1.3.6.1.4.1.47477.10.21.17.3.34
		link17_1R4AlarmPower OBJECT-TYPE
			SYNTAX DisplayString
			MAX-ACCESS read-write
			STATUS current
			DESCRIPTION
				"get or set the power alarm threshold of 1R4 in link17."
			::= { link17OBP 34 }

--  1.3.6.1.4.1.47477.10.21.17.3.45
		-- 1.3.6.1.4.1.47477.10.21.17.3.45
		link17_2R1AlarmPower OBJECT-TYPE
			SYNTAX DisplayString
			MAX-ACCESS read-write
			STATUS current
			DESCRIPTION
				"get or set the power alarm threshold of 2R1 in link17."
			::= { link17OBP 45 }
			
--  1.3.6.1.4.1.47477.10.21.17.3.46
		-- 1.3.6.1.4.1.47477.10.21.17.3.46
		link17_2R2AlarmPower OBJECT-TYPE
			SYNTAX DisplayString
			MAX-ACCESS read-write
			STATUS current
			DESCRIPTION
				"get or set the power alarm threshold of 2R2 in link17."
			::= { link17OBP 46 }

--  1.3.6.1.4.1.47477.10.21.17.3.47
		-- 1.3.6.1.4.1.47477.10.21.17.3.47
		link17_2R3AlarmPower OBJECT-TYPE
			SYNTAX DisplayString
			MAX-ACCESS read-write
			STATUS current
			DESCRIPTION
				"get or set the power alarm threshold of 2R3 in link17."
			::= { link17OBP 47 }
			
--  1.3.6.1.4.1.47477.10.21.17.3.48
		-- 1.3.6.1.4.1.47477.10.21.17.3.48
		link17_2R4AlarmPower OBJECT-TYPE
			SYNTAX DisplayString
			MAX-ACCESS read-write
			STATUS current
			DESCRIPTION
				"get or set the power alarm threshold of 2R4 in link17."
			::= { link17OBP 48 }
			
--  1.3.6.1.4.1.47477.10.21.17.3.11
		-- 1.3.6.1.4.1.47477.10.21.17.3.11
		link17_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link17OBP 11 }
			
--  1.3.6.1.4.1.47477.10.21.17.3.67
		-- 1.3.6.1.4.1.47477.10.21.17.3.67
		link17_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link17OBP 67 }
			
--  1.3.6.1.4.1.47477.10.21.17.3.68
		-- 1.3.6.1.4.1.47477.10.21.17.3.68
		link17_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link17OBP 68 }
			
--  1.3.6.1.4.1.47477.10.21.17.3.12
		-- 1.3.6.1.4.1.47477.10.21.17.3.12
		link17_ReturnDelay OBJECT-TYPE
			--SYNTAX Integer32
			SYNTAX Integer32
			MAX-ACCESS read-write
			STATUS current
			DESCRIPTION
				"get or set how long link17 takes to return to automatic mode."
			::= { link17OBP 12 }
			
--  1.3.6.1.4.1.47477.10.21.17.3.13
		-- 1.3.6.1.4.1.47477.10.21.17.3.13
		link17_BackMode OBJECT-TYPE
			SYNTAX INTEGER
				{
				autoNoBack(0),
				autoBack(1)
				}
			MAX-ACCESS read-write
			STATUS current
			DESCRIPTION
				"get or set the back mode of link17."
			::= { link17OBP 13 }

		
--  1.3.6.1.4.1.47477.10.21.17.3.14
		-- 1.3.6.1.4.1.47477.10.21.17.3.14
		link17_BackDelay OBJECT-TYPE
			SYNTAX Integer32
			MAX-ACCESS read-write
			STATUS current
			DESCRIPTION
				"get or set the back delay."
			::= { link17OBP 14 }

--  1.3.6.1.4.1.47477.10.21.17.3.15
		-- 1.3.6.1.4.1.47477.10.21.17.3.15
		link17_ActiveHeartSwitch OBJECT-TYPE
			SYNTAX INTEGER
				{
				off(0),
				on(1)
				}
			MAX-ACCESS read-write
			STATUS current
			DESCRIPTION
				"get or set the switch status of active heartbeat."
			::= { link17OBP 15 }

		
--  1.3.6.1.4.1.47477.10.21.17.3.16
		-- 1.3.6.1.4.1.47477.10.21.17.3.16
		link17_ActiveSendInterval OBJECT-TYPE
			SYNTAX Integer32
			MAX-ACCESS read-write
			STATUS current
			DESCRIPTION
				"get or set the send interval of active heartbeat."
			::= { link17OBP 16 }		

--  1.3.6.1.4.1.47477.10.21.17.3.17
		-- 1.3.6.1.4.1.47477.10.21.17.3.17
		link17_ActiveTimeOut OBJECT-TYPE
			SYNTAX Integer32
			MAX-ACCESS read-write
			STATUS current
			DESCRIPTION
				"get or set how long the active heartbeat send timeout."
			::= { link17OBP 17 }

--  1.3.6.1.4.1.47477.10.21.17.3.18
		-- 1.3.6.1.4.1.47477.10.21.17.3.18
		link17_ActiveLossBypass OBJECT-TYPE
			SYNTAX Integer32
			MAX-ACCESS read-write
			STATUS current
			DESCRIPTION
				"get or set the bypass for active heartbeat packet loss."
			::= { link17OBP 18 }

--  1.3.6.1.4.1.47477.10.21.17.3.19
		-- 1.3.6.1.4.1.47477.10.21.17.3.19
		link17_PingIpAddress OBJECT-TYPE
			SYNTAX IpAddress
			MAX-ACCESS read-write
			STATUS current
			DESCRIPTION
				"get or set the ping ip address of link17."
			::= { link17OBP 19 }

--  1.3.6.1.4.1.47477.10.21.17.3.20
		-- 1.3.6.1.4.1.47477.10.21.17.3.20
		link17_PassiveHeartSwitch OBJECT-TYPE
			SYNTAX INTEGER
				{
				off(0),
				on(1)
				}
			MAX-ACCESS read-write
			STATUS current
			DESCRIPTION
				"get or set the switch status of passive heartbeat."
			::= { link17OBP 20 }
	

--  1.3.6.1.4.1.47477.10.21.17.3.21
		-- 1.3.6.1.4.1.47477.10.21.17.3.21
		link17_PassiveTimeOut OBJECT-TYPE
			SYNTAX Integer32
			MAX-ACCESS read-write
			STATUS current
			DESCRIPTION
				"get or set how long the passive heartbeat send timeout."
			::= { link17OBP 21 }

--  1.3.6.1.4.1.47477.10.21.17.3.22
		-- 1.3.6.1.4.1.47477.10.21.17.3.22
		link17_PassiveLossBypass OBJECT-TYPE
			SYNTAX Integer32
			MAX-ACCESS read-write
			STATUS current
			DESCRIPTION
				"get or set the bypass for passive heartbeat packet loss."
			::= { link17OBP 22 }

--  1.3.6.1.4.1.47477.10.21.17.3.23
		-- 1.3.6.1.4.1.47477.10.21.17.3.23
		link17_SwitchProtect OBJECT-TYPE
			SYNTAX INTEGER
				{
				off(0),
				on(1)
				}
			MAX-ACCESS read-write
			STATUS current
			DESCRIPTION
				"get or set the switch protection status of link17."
			::= { link17OBP 23 }
			
--  1.3.6.1.4.1.47477.10.21.17.3.24
		-- 1.3.6.1.4.1.47477.10.21.17.3.24
		link17_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link17OBP 24 }		

--  1.3.6.1.4.1.47477.10.21.17.3.25
		-- 1.3.6.1.4.1.47477.10.21.17.3.25
		link17_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link17OBP 25 }	

--  1.3.6.1.4.1.47477.10.21.17.3.26
		-- 1.3.6.1.4.1.47477.10.21.17.3.26
		link17_PowerAlarmStatus OBJECT-TYPE
			SYNTAX INTEGER
				{
				off(0),
				alarm(1),
				normal(2),
				na(3)
				}
			MAX-ACCESS read-only
			STATUS current
			DESCRIPTION
				"get whether a power alarm is generated."
			::= { link17OBP 26 }	


-- 1.3.6.1.4.1.47477.10.21.17.3.50.1
	link17_WorkModeChange 	OBJECT-TYPE    
    SYNTAX INTEGER	{
				manualMode(0),
				autoMode(1)
		}
	MAX-ACCESS read-only
	STATUS current
    DESCRIPTION
        "The Link mode Changed."
    ::= {link17OBPTrap 1}

-- 1.3.6.1.4.1.47477.10.21.17.3.50.2
	link17_StateChange 	OBJECT-TYPE    
    SYNTAX INTEGER	{
				bypass(0),
				primary(1)
		}
	MAX-ACCESS read-only
	STATUS current
    DESCRIPTION
        "The Link State(Channel) Changed."
    ::= {link17OBPTrap 2}

-- 1.3.6.1.4.1.47477.10.21.17.3.50.3
	link17_R1WaveSet 	OBJECT-TYPE    
    SYNTAX INTEGER	{
				w1310nm(0),
				w1550nm(1)
		}
	MAX-ACCESS read-only
	STATUS current
    DESCRIPTION
        "Set The link17 R1 Wave."
    ::= {link17OBPTrap 3}

-- 1.3.6.1.4.1.47477.10.21.17.3.50.4
	link17_R2WaveSet 	OBJECT-TYPE    
    SYNTAX INTEGER	{
				w1310nm(0),
				w1550nm(1)
		}
	MAX-ACCESS read-only
	STATUS current
    DESCRIPTION
        "Set The link17 R2 Wave."
    ::= {link17OBPTrap 4}			

-- 1.3.6.1.4.1.47477.10.21.17.3.50.5
	link17_R3WaveSet 	OBJECT-TYPE    
    SYNTAX INTEGER	{
				w1310nm(0),
				w1550nm(1)
		}
	MAX-ACCESS read-only
	STATUS current
    DESCRIPTION
        "Set The link17 R3 Wave."
    ::= {link17OBPTrap 5}

-- 1.3.6.1.4.1.47477.10.21.17.3.50.6
	link17_R4WaveSet 	OBJECT-TYPE    
    SYNTAX INTEGER	{
				w1310nm(0),
				w1550nm(1)
		}
	MAX-ACCESS read-only
	STATUS current
    DESCRIPTION
        "Set The link17 R4 Wave."
    ::= {link17OBPTrap 6}	
	
-- 1.3.6.1.4.1.47477.10.21.17.3.50.7
	link17_R1AlarmSet 	OBJECT-TYPE    
    SYNTAX DisplayString
	MAX-ACCESS read-only
	STATUS current
    DESCRIPTION
        "Set The link17 R1 Alarm Threshold."
    ::= {link17OBPTrap 7}

-- 1.3.6.1.4.1.47477.10.21.17.3.50.8
	link17_R2AlarmSet 	OBJECT-TYPE    
    SYNTAX DisplayString
	MAX-ACCESS read-only
	STATUS current
    DESCRIPTION
        "Set The link17 R2 Alarm Threshold."
    ::= {link17OBPTrap 8}
	
-- 1.3.6.1.4.1.47477.10.21.17.3.50.9
	link17_R3AlarmSet 	OBJECT-TYPE    
    SYNTAX DisplayString
	MAX-ACCESS read-only
	STATUS current
    DESCRIPTION
        "Set The link17 R3 Alarm Threshold."
    ::= {link17OBPTrap 9}

-- 1.3.6.1.4.1.47477.10.21.17.3.50.10
	link17_R4AlarmSet 	OBJECT-TYPE    
    SYNTAX DisplayString
	MAX-ACCESS read-only
	STATUS current
    DESCRIPTION
        "Set The link17 R4 Alarm Threshold."
    ::= {link17OBPTrap 10}	
	
	
-- 1.3.6.1.4.1.47477.10.21.17.3.50.11
	link17_1R1AlarmSet 	OBJECT-TYPE    
    SYNTAX DisplayString
	MAX-ACCESS read-only
	STATUS current
    DESCRIPTION
        "Set The link17 1R1 Alarm Threshold."
    ::= {link17OBPTrap 11}

-- 1.3.6.1.4.1.47477.10.21.17.3.50.12
	link17_2R1AlarmSet 	OBJECT-TYPE    
    SYNTAX DisplayString
	MAX-ACCESS read-only
	STATUS current
    DESCRIPTION
        "Set The link17 2R1 Alarm Threshold."
    ::= {link17OBPTrap 12}
	
-- 1.3.6.1.4.1.47477.10.21.17.3.50.13
	link17_1R2AlarmSet 	OBJECT-TYPE    
    SYNTAX DisplayString
	MAX-ACCESS read-only
	STATUS current
    DESCRIPTION
        "Set The link17 1R2 Alarm Threshold."
    ::= {link17OBPTrap 13}

-- 1.3.6.1.4.1.47477.10.21.17.3.50.14
	link17_2R2AlarmSet 	OBJECT-TYPE    
    SYNTAX DisplayString
	MAX-ACCESS read-only
	STATUS current
    DESCRIPTION
        "Set The link17 2R2 Alarm Threshold."
    ::= {link17OBPTrap 14}
	
-- 1.3.6.1.4.1.47477.10.21.17.3.50.15
	link17_1R3AlarmSet 	OBJECT-TYPE    
    SYNTAX DisplayString
	MAX-ACCESS read-only
	STATUS current
    DESCRIPTION
        "Set The link17 1R3 Alarm Threshold."
    ::= {link17OBPTrap 15}

-- 1.3.6.1.4.1.47477.10.21.17.3.50.16
	link17_2R3AlarmSet 	OBJECT-TYPE    
    SYNTAX DisplayString
	MAX-ACCESS read-only
	STATUS current
    DESCRIPTION
        "Set The link17 2R3 Alarm Threshold."
    ::= {link17OBPTrap 16}
	
-- 1.3.6.1.4.1.47477.10.21.17.3.50.17
	link17_1R4AlarmSet 	OBJECT-TYPE    
    SYNTAX DisplayString
	MAX-ACCESS read-only
	STATUS current
    DESCRIPTION
        "Set The link17 1R4 Alarm Threshold."
    ::= {link17OBPTrap 17}

-- 1.3.6.1.4.1.47477.10.21.17.3.50.18
	link17_2R4AlarmSet 	OBJECT-TYPE    
    SYNTAX DisplayString
	MAX-ACCESS read-only
	STATUS current
    DESCRIPTION
        "Set The link17 2R4 Alarm Threshold."
    ::= {link17OBPTrap 18}
	
-- 1.3.6.1.4.1.47477.10.21.17.3.50.19
	link17_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link17 PowerAlarmBypass2 Changed."
    ::= {link17OBPTrap 19}
	
-- 1.3.6.1.4.1.47477.10.21.17.3.50.20
	link17_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link17 PowerAlarmBypass4 Changed."
    ::= {link17OBPTrap 20}	
	
-- 1.3.6.1.4.1.47477.10.21.17.3.50.21
	link17_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link17 PowerAlarmBypass8 Changed."
    ::= {link17OBPTrap 21}
	
-- 1.3.6.1.4.1.47477.10.21.17.3.50.22
	link17_powerAlarmR1 	OBJECT-TYPE    
    SYNTAX DisplayString
	MAX-ACCESS read-only
	STATUS current
    DESCRIPTION
        "Set The link17 R1 Power Status Alarm."
    ::= {link17OBPTrap 22}
	
-- 1.3.6.1.4.1.47477.10.21.17.3.50.23
	link17_powerAlarmR2 	OBJECT-TYPE    
    SYNTAX DisplayString
	MAX-ACCESS read-only
	STATUS current
    DESCRIPTION
        "Set The link17 R2 Power Status Alarm."
    ::= {link17OBPTrap 23}
	
-- 1.3.6.1.4.1.47477.10.21.17.3.50.24
	link17_powerAlarmR3 	OBJECT-TYPE    
    SYNTAX DisplayString
	MAX-ACCESS read-only
	STATUS current
    DESCRIPTION
        "Set The link17 R3 Power Status Alarm."
    ::= {link17OBPTrap 24}
	
-- 1.3.6.1.4.1.47477.10.21.17.3.50.25
	link17_powerAlarmR4 	OBJECT-TYPE    
    SYNTAX DisplayString
	MAX-ACCESS read-only
	STATUS current
    DESCRIPTION
        "Set The link17 R4 Power Status Alarm."
    ::= {link17OBPTrap 25}
	
	
-- 1.3.6.1.4.1.47477.10.21.17.3.50.26
	link17_powerAlarm1R1 	OBJECT-TYPE    
    SYNTAX DisplayString
	MAX-ACCESS read-only
	STATUS current
    DESCRIPTION
        "Set The link17 1R1 Power Status Alarm."
    ::= {link17OBPTrap 26}
	
-- 1.3.6.1.4.1.47477.10.21.17.3.50.27
	link17_powerAlarm2R1 	OBJECT-TYPE    
    SYNTAX DisplayString
	MAX-ACCESS read-only
	STATUS current
    DESCRIPTION
        "Set The link17 2R1 Power Status Alarm."
    ::= {link17OBPTrap 27}
	
-- 1.3.6.1.4.1.47477.10.21.17.3.50.28
	link17_powerAlarm1R2 	OBJECT-TYPE    
    SYNTAX DisplayString
	MAX-ACCESS read-only
	STATUS current
    DESCRIPTION
        "Set The link17 1R2 Power Status Alarm."
    ::= {link17OBPTrap 28}
	
-- 1.3.6.1.4.1.47477.10.21.17.3.50.29
	link17_powerAlarm2R2 	OBJECT-TYPE    
    SYNTAX DisplayString
	MAX-ACCESS read-only
	STATUS current
    DESCRIPTION
        "Set The link17 2R2 Power Status Alarm."
    ::= {link17OBPTrap 29}
	
-- 1.3.6.1.4.1.47477.10.21.17.3.50.30
	link17_powerAlarm1R3 	OBJECT-TYPE    
    SYNTAX DisplayString
	MAX-ACCESS read-only
	STATUS current
    DESCRIPTION
        "Set The link17 1R3 Power Status Alarm."
    ::= {link17OBPTrap 30}
	
-- 1.3.6.1.4.1.47477.10.21.17.3.50.31
	link17_powerAlarm2R3 	OBJECT-TYPE    
    SYNTAX DisplayString
	MAX-ACCESS read-only
	STATUS current
    DESCRIPTION
        "Set The link17 2R1 Power Status Alarm."
    ::= {link17OBPTrap 31}
	
-- 1.3.6.1.4.1.47477.10.21.17.3.50.32
	link17_powerAlarm1R4 	OBJECT-TYPE    
    SYNTAX DisplayString
	MAX-ACCESS read-only
	STATUS current
    DESCRIPTION
        "Set The link17 1R4 Power Status Alarm."
    ::= {link17OBPTrap 32}
	
-- 1.3.6.1.4.1.47477.10.21.17.3.50.33
	link17_powerAlarm2R4 	OBJECT-TYPE    
    SYNTAX DisplayString
	MAX-ACCESS read-only
	STATUS current
    DESCRIPTION
        "Set The link17 2R4 Power Status Alarm."
    ::= {link17OBPTrap 33}
	
--  1.3.6.1.4.1.47477.10.21.18.3.1
		-- 1.3.6.1.4.1.47477.10.21.18.3.1
		link18_State OBJECT-TYPE
			SYNTAX INTEGER
				{
				off(0),
				on(1)
				}
			MAX-ACCESS read-only
			STATUS current
			DESCRIPTION
				"get the information about whether link18 is working."
			::= { link18OBP 1 }

		
--  1.3.6.1.4.1.47477.10.21.18.3.2
		-- 1.3.6.1.4.1.47477.10.21.18.3.2
		link18_DeviceType OBJECT-TYPE
			SYNTAX DisplayString
			MAX-ACCESS read-only
			STATUS current
			DESCRIPTION
				"get the type of card in link18."
			::= { link18OBP 2 }

			
--  1.3.6.1.4.1.47477.10.21.18.3.3
		-- 1.3.6.1.4.1.47477.10.21.18.3.3
		link18_WorkMode OBJECT-TYPE
			SYNTAX INTEGER
				{
				manualMode(0),
				autoMode(1)
				}
			MAX-ACCESS read-write
			STATUS current
			DESCRIPTION
				"get or set link18's work mode."
			::= { link18OBP 3 }

		
--  1.3.6.1.4.1.47477.10.21.18.3.4
		-- 1.3.6.1.4.1.47477.10.21.18.3.4
		link18_Channel OBJECT-TYPE
			SYNTAX INTEGER
				{
				bypass(0),
				primary(1)
				}
			MAX-ACCESS read-write
			STATUS current
			DESCRIPTION
				"get or set the channel in which link18 works."
			::= { link18OBP 4 }


--  1.3.6.1.4.1.47477.10.21.18.3.5
		-- 1.3.6.1.4.1.47477.10.21.18.3.5
		link18_R1Power OBJECT-TYPE
			SYNTAX DisplayString
			MAX-ACCESS read-only
			STATUS current
			DESCRIPTION
				"get the power of R1 in link18."
			::= { link18OBP 5 }

		
--  1.3.6.1.4.1.47477.10.21.18.3.6
		-- 1.3.6.1.4.1.47477.10.21.18.3.6
		link18_R2Power OBJECT-TYPE
			SYNTAX DisplayString
			MAX-ACCESS read-only
			STATUS current
			DESCRIPTION
				"get the power of R2 in link18."
			::= { link18OBP 6 }
			
--  1.3.6.1.4.1.47477.10.21.18.3.35
		-- 1.3.6.1.4.1.47477.10.21.18.3.35
		link18_R3Power OBJECT-TYPE
			SYNTAX DisplayString
			MAX-ACCESS read-only
			STATUS current
			DESCRIPTION
				"get the power of R3 in link18."
			::= { link18OBP 35 }
			
--  1.3.6.1.4.1.47477.10.21.18.3.36
		-- 1.3.6.1.4.1.47477.10.21.18.3.36
		link18_R4Power OBJECT-TYPE
			SYNTAX DisplayString
			MAX-ACCESS read-only
			STATUS current
			DESCRIPTION
				"get the power of R4 in link18."
			::= { link18OBP 36 }		
		
--  1.3.6.1.4.1.47477.10.21.18.3.7
		-- 1.3.6.1.4.1.47477.10.21.18.3.7
		link18_R1Wave OBJECT-TYPE
			SYNTAX INTEGER
				{
				w1310nm(0),
				w1550nm(1),
				na(2)
				}
			MAX-ACCESS read-write
			STATUS current
			DESCRIPTION
				"get or set the wave length of R1 in link18."
			::= { link18OBP 7 }

		
--  1.3.6.1.4.1.47477.10.21.18.3.8
		-- 1.3.6.1.4.1.47477.10.21.18.3.8
		link18_R2Wave OBJECT-TYPE
			SYNTAX INTEGER
				{
				w1310nm(0),
				w1550nm(1),
				na(2)
				}
			MAX-ACCESS read-write
			STATUS current
			DESCRIPTION
				"get or set the wave length of R2 in link18."
			::= { link18OBP 8 }


--  1.3.6.1.4.1.47477.10.21.18.3.27
		-- 1.3.6.1.4.1.47477.10.21.18.3.27
		link18_R3Wave OBJECT-TYPE
			SYNTAX INTEGER
				{
				w1310nm(0),
				w1550nm(1),
				na(2)
				}
			MAX-ACCESS read-write
			STATUS current
			DESCRIPTION
				"get or set the wave length of R3 in link18."
			::= { link18OBP 27 }

		
--  1.3.6.1.4.1.47477.10.21.18.3.28
		-- 1.3.6.1.4.1.47477.10.21.18.3.28
		link18_R4Wave OBJECT-TYPE
			SYNTAX INTEGER
				{
				w1310nm(0),
				w1550nm(1),
				na(2)
				}
			MAX-ACCESS read-write
			STATUS current
			DESCRIPTION
				"get or set the wave length of R4 in link18."
			::= { link18OBP 28 }
			
--  1.3.6.1.4.1.47477.10.21.18.3.9
		-- 1.3.6.1.4.1.47477.10.21.18.3.9
		link18_R1AlarmPower OBJECT-TYPE
			SYNTAX DisplayString
			MAX-ACCESS read-write
			STATUS current
			DESCRIPTION
				"get or set the power alarm threshold of R1 in link18."
			::= { link18OBP 9 }

		
--  1.3.6.1.4.1.47477.10.21.18.3.10
		-- 1.3.6.1.4.1.47477.10.21.18.3.10
		link18_R2AlarmPower OBJECT-TYPE
			SYNTAX DisplayString
			MAX-ACCESS read-write
			STATUS current
			DESCRIPTION
				"get or set the power alarm threshold of R2 in link18."
			::= { link18OBP 10 }


--  1.3.6.1.4.1.47477.10.21.18.3.29
		-- 1.3.6.1.4.1.47477.10.21.18.3.29
		link18_R3AlarmPower OBJECT-TYPE
			SYNTAX DisplayString
			MAX-ACCESS read-write
			STATUS current
			DESCRIPTION
				"get or set the power alarm threshold of R3 in link18."
			::= { link18OBP 29 }

		
--  1.3.6.1.4.1.47477.10.21.18.3.30
		-- 1.3.6.1.4.1.47477.10.21.18.3.30
		link18_R4AlarmPower OBJECT-TYPE
			SYNTAX DisplayString
			MAX-ACCESS read-write
			STATUS current
			DESCRIPTION
				"get or set the power alarm threshold of R4 in link18."
			::= { link18OBP 30 }

-- OBP4
--  1.3.6.1.4.1.47477.10.21.18.3.37
		-- 1.3.6.1.4.1.47477.10.21.18.3.37
		link18_1R1Power OBJECT-TYPE
			SYNTAX DisplayString
			MAX-ACCESS read-only
			STATUS current
			DESCRIPTION
				"get the power of 1R1 in link18."
			::= { link18OBP 37 }
			
--  1.3.6.1.4.1.47477.10.21.18.3.38
		-- 1.3.6.1.4.1.47477.10.21.18.3.38
		link18_1R2Power OBJECT-TYPE
			SYNTAX DisplayString
			MAX-ACCESS read-only
			STATUS current
			DESCRIPTION
				"get the power of 1R2 in link18."
			::= { link18OBP 38 }

--  1.3.6.1.4.1.47477.10.21.18.3.39
		-- 1.3.6.1.4.1.47477.10.21.18.3.39
		link18_1R3Power OBJECT-TYPE
			SYNTAX DisplayString
			MAX-ACCESS read-only
			STATUS current
			DESCRIPTION
				"get the power of 1R3 in link18."
			::= { link18OBP 39 }
			
--  1.3.6.1.4.1.47477.10.21.18.3.40
		-- 1.3.6.1.4.1.47477.10.21.18.3.40
		link18_1R4Power OBJECT-TYPE
			SYNTAX DisplayString
			MAX-ACCESS read-only
			STATUS current
			DESCRIPTION
				"get the power of 1R4 in link18."
			::= { link18OBP 40 }

--  1.3.6.1.4.1.47477.10.21.18.3.41
		-- 1.3.6.1.4.1.47477.10.21.18.3.41
		link18_2R1Power OBJECT-TYPE
			SYNTAX DisplayString
			MAX-ACCESS read-only
			STATUS current
			DESCRIPTION
				"get the power of 2R1 in link18."
			::= { link18OBP 41 }
			
--  1.3.6.1.4.1.47477.10.21.18.3.42
		-- 1.3.6.1.4.1.47477.10.21.18.3.42
		link18_2R2Power OBJECT-TYPE
			SYNTAX DisplayString
			MAX-ACCESS read-only
			STATUS current
			DESCRIPTION
				"get the power of 2R2 in link18."
			::= { link18OBP 42 }

--  1.3.6.1.4.1.47477.10.21.18.3.41
		-- 1.3.6.1.4.1.47477.10.21.18.3.43
		link18_2R3Power OBJECT-TYPE
			SYNTAX DisplayString
			MAX-ACCESS read-only
			STATUS current
			DESCRIPTION
				"get the power of 2R3 in link18."
			::= { link18OBP 43 }
			
--  1.3.6.1.4.1.47477.10.21.18.3.42
		-- 1.3.6.1.4.1.47477.10.21.18.3.44
		link18_2R4Power OBJECT-TYPE
			SYNTAX DisplayString
			MAX-ACCESS read-only
			STATUS current
			DESCRIPTION
				"get the power of 2R4 in link18."
			::= { link18OBP 44 }
			
--  1.3.6.1.4.1.47477.10.21.18.3.49
		-- 1.3.6.1.4.1.47477.10.21.18.3.49
		link18_1R1Wave OBJECT-TYPE
			SYNTAX INTEGER
				{
				w850nm(0),
				na(2)
				}
			MAX-ACCESS read-only
			STATUS current
			DESCRIPTION
				"get the wave length of 1R1 in link18."
			::= { link18OBP 49 }
		
--  1.3.6.1.4.1.47477.10.21.18.3.60
		-- 1.3.6.1.4.1.47477.10.21.18.3.60
		link18_1R2Wave OBJECT-TYPE
			SYNTAX INTEGER
				{
				w850nm(0),
				na(2)
				}
			MAX-ACCESS read-only
			STATUS current
			DESCRIPTION
				"get the wave length of 1R2 in link18."
			::= { link18OBP 60 }

--  1.3.6.1.4.1.47477.10.21.18.3.61
		-- 1.3.6.1.4.1.47477.10.21.18.3.61
		link18_1R3Wave OBJECT-TYPE
			SYNTAX INTEGER
				{
				w850nm(0),
				na(2)
				}
			MAX-ACCESS read-only
			STATUS current
			DESCRIPTION
				"get the wave length of 1R3 in link18."
			::= { link18OBP 61 }

		
--  1.3.6.1.4.1.47477.10.21.18.3.62
		-- 1.3.6.1.4.1.47477.10.21.18.3.62
		link18_1R4Wave OBJECT-TYPE
			SYNTAX INTEGER
				{
				w850nm(0),
				na(2)
				}
			MAX-ACCESS read-only
			STATUS current
			DESCRIPTION
				"get the wave length of 1R4 in link18."
			::= { link18OBP 62 }
	
--  1.3.6.1.4.1.47477.10.21.18.3.63
		-- 1.3.6.1.4.1.47477.10.21.18.3.63
		link18_2R1Wave OBJECT-TYPE
			SYNTAX INTEGER
				{
				w850nm(0),
				na(2)
				}
			MAX-ACCESS read-only
			STATUS current
			DESCRIPTION
				"get the wave length of 2R1 in link18."
			::= { link18OBP 63 }

		
--  1.3.6.1.4.1.47477.10.21.18.3.64
		-- 1.3.6.1.4.1.47477.10.21.18.3.64
		link18_2R2Wave OBJECT-TYPE
			SYNTAX INTEGER
				{
				w850nm(0),
				na(2)
				}
			MAX-ACCESS read-only
			STATUS current
			DESCRIPTION
				"get the wave length of 2R2 in link18."
			::= { link18OBP 64 }	
	
--  1.3.6.1.4.1.47477.10.21.18.3.65
		-- 1.3.6.1.4.1.47477.10.21.18.3.65
		link18_2R3Wave OBJECT-TYPE
			SYNTAX INTEGER
				{
				w850nm(0),
				na(2)
				}
			MAX-ACCESS read-only
			STATUS current
			DESCRIPTION
				"get the wave length of 2R3 in link18."
			::= { link18OBP 65 }

		
--  1.3.6.1.4.1.47477.10.21.18.3.66
		-- 1.3.6.1.4.1.47477.10.21.18.3.66
		link18_2R4Wave OBJECT-TYPE
			SYNTAX INTEGER
				{
				w850nm(0),
				na(2)
				}
			MAX-ACCESS read-only
			STATUS current
			DESCRIPTION
				"get the wave length of 2R4 in link18."
			::= { link18OBP 66 }	
			
--  1.3.6.1.4.1.47477.10.21.18.3.31
		-- 1.3.6.1.4.1.47477.10.21.18.3.31
		link18_1R1AlarmPower OBJECT-TYPE
			SYNTAX DisplayString
			MAX-ACCESS read-write
			STATUS current
			DESCRIPTION
				"get or set the power alarm threshold of 1R1 in link18."
			::= { link18OBP 31 }
			
--  1.3.6.1.4.1.47477.10.21.18.3.32
		-- 1.3.6.1.4.1.47477.10.21.18.3.32
		link18_1R2AlarmPower OBJECT-TYPE
			SYNTAX DisplayString
			MAX-ACCESS read-write
			STATUS current
			DESCRIPTION
				"get or set the power alarm threshold of 1R2 in link18."
			::= { link18OBP 32 }

--  1.3.6.1.4.1.47477.10.21.18.3.33
		-- 1.3.6.1.4.1.47477.10.21.18.3.33
		link18_1R3AlarmPower OBJECT-TYPE
			SYNTAX DisplayString
			MAX-ACCESS read-write
			STATUS current
			DESCRIPTION
				"get or set the power alarm threshold of 1R3 in link18."
			::= { link18OBP 33 }
			
--  1.3.6.1.4.1.47477.10.21.18.3.34
		-- 1.3.6.1.4.1.47477.10.21.18.3.34
		link18_1R4AlarmPower OBJECT-TYPE
			SYNTAX DisplayString
			MAX-ACCESS read-write
			STATUS current
			DESCRIPTION
				"get or set the power alarm threshold of 1R4 in link18."
			::= { link18OBP 34 }

--  1.3.6.1.4.1.47477.10.21.18.3.45
		-- 1.3.6.1.4.1.47477.10.21.18.3.45
		link18_2R1AlarmPower OBJECT-TYPE
			SYNTAX DisplayString
			MAX-ACCESS read-write
			STATUS current
			DESCRIPTION
				"get or set the power alarm threshold of 2R1 in link18."
			::= { link18OBP 45 }
			
--  1.3.6.1.4.1.47477.10.21.18.3.46
		-- 1.3.6.1.4.1.47477.10.21.18.3.46
		link18_2R2AlarmPower OBJECT-TYPE
			SYNTAX DisplayString
			MAX-ACCESS read-write
			STATUS current
			DESCRIPTION
				"get or set the power alarm threshold of 2R2 in link18."
			::= { link18OBP 46 }

--  1.3.6.1.4.1.47477.10.21.18.3.47
		-- 1.3.6.1.4.1.47477.10.21.18.3.47
		link18_2R3AlarmPower OBJECT-TYPE
			SYNTAX DisplayString
			MAX-ACCESS read-write
			STATUS current
			DESCRIPTION
				"get or set the power alarm threshold of 2R3 in link18."
			::= { link18OBP 47 }
			
--  1.3.6.1.4.1.47477.10.21.18.3.48
		-- 1.3.6.1.4.1.47477.10.21.18.3.48
		link18_2R4AlarmPower OBJECT-TYPE
			SYNTAX DisplayString
			MAX-ACCESS read-write
			STATUS current
			DESCRIPTION
				"get or set the power alarm threshold of 2R4 in link18."
			::= { link18OBP 48 }
			
--  1.3.6.1.4.1.47477.10.21.18.3.11
		-- 1.3.6.1.4.1.47477.10.21.18.3.11
		link18_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link18OBP 11 }
			
--  1.3.6.1.4.1.47477.10.21.18.3.67
		-- 1.3.6.1.4.1.47477.10.21.18.3.67
		link18_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link18OBP 67 }
			
--  1.3.6.1.4.1.47477.10.21.18.3.68
		-- 1.3.6.1.4.1.47477.10.21.18.3.68
		link18_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link18OBP 68 }
			
--  1.3.6.1.4.1.47477.10.21.18.3.12
		-- 1.3.6.1.4.1.47477.10.21.18.3.12
		link18_ReturnDelay OBJECT-TYPE
			--SYNTAX Integer32
			SYNTAX Integer32
			MAX-ACCESS read-write
			STATUS current
			DESCRIPTION
				"get or set how long link18 takes to return to automatic mode."
			::= { link18OBP 12 }
			
--  1.3.6.1.4.1.47477.10.21.18.3.13
		-- 1.3.6.1.4.1.47477.10.21.18.3.13
		link18_BackMode OBJECT-TYPE
			SYNTAX INTEGER
				{
				autoNoBack(0),
				autoBack(1)
				}
			MAX-ACCESS read-write
			STATUS current
			DESCRIPTION
				"get or set the back mode of link18."
			::= { link18OBP 13 }

		
--  1.3.6.1.4.1.47477.10.21.18.3.14
		-- 1.3.6.1.4.1.47477.10.21.18.3.14
		link18_BackDelay OBJECT-TYPE
			SYNTAX Integer32
			MAX-ACCESS read-write
			STATUS current
			DESCRIPTION
				"get or set the back delay."
			::= { link18OBP 14 }

--  1.3.6.1.4.1.47477.10.21.18.3.15
		-- 1.3.6.1.4.1.47477.10.21.18.3.15
		link18_ActiveHeartSwitch OBJECT-TYPE
			SYNTAX INTEGER
				{
				off(0),
				on(1)
				}
			MAX-ACCESS read-write
			STATUS current
			DESCRIPTION
				"get or set the switch status of active heartbeat."
			::= { link18OBP 15 }

		
--  1.3.6.1.4.1.47477.10.21.18.3.16
		-- 1.3.6.1.4.1.47477.10.21.18.3.16
		link18_ActiveSendInterval OBJECT-TYPE
			SYNTAX Integer32
			MAX-ACCESS read-write
			STATUS current
			DESCRIPTION
				"get or set the send interval of active heartbeat."
			::= { link18OBP 16 }		

--  1.3.6.1.4.1.47477.10.21.18.3.17
		-- 1.3.6.1.4.1.47477.10.21.18.3.17
		link18_ActiveTimeOut OBJECT-TYPE
			SYNTAX Integer32
			MAX-ACCESS read-write
			STATUS current
			DESCRIPTION
				"get or set how long the active heartbeat send timeout."
			::= { link18OBP 17 }

--  1.3.6.1.4.1.47477.10.21.18.3.18
		-- 1.3.6.1.4.1.47477.10.21.18.3.18
		link18_ActiveLossBypass OBJECT-TYPE
			SYNTAX Integer32
			MAX-ACCESS read-write
			STATUS current
			DESCRIPTION
				"get or set the bypass for active heartbeat packet loss."
			::= { link18OBP 18 }

--  1.3.6.1.4.1.47477.10.21.18.3.19
		-- 1.3.6.1.4.1.47477.10.21.18.3.19
		link18_PingIpAddress OBJECT-TYPE
			SYNTAX IpAddress
			MAX-ACCESS read-write
			STATUS current
			DESCRIPTION
				"get or set the ping ip address of link18."
			::= { link18OBP 19 }

--  1.3.6.1.4.1.47477.10.21.18.3.20
		-- 1.3.6.1.4.1.47477.10.21.18.3.20
		link18_PassiveHeartSwitch OBJECT-TYPE
			SYNTAX INTEGER
				{
				off(0),
				on(1)
				}
			MAX-ACCESS read-write
			STATUS current
			DESCRIPTION
				"get or set the switch status of passive heartbeat."
			::= { link18OBP 20 }
	

--  1.3.6.1.4.1.47477.10.21.18.3.21
		-- 1.3.6.1.4.1.47477.10.21.18.3.21
		link18_PassiveTimeOut OBJECT-TYPE
			SYNTAX Integer32
			MAX-ACCESS read-write
			STATUS current
			DESCRIPTION
				"get or set how long the passive heartbeat send timeout."
			::= { link18OBP 21 }

--  1.3.6.1.4.1.47477.10.21.18.3.22
		-- 1.3.6.1.4.1.47477.10.21.18.3.22
		link18_PassiveLossBypass OBJECT-TYPE
			SYNTAX Integer32
			MAX-ACCESS read-write
			STATUS current
			DESCRIPTION
				"get or set the bypass for passive heartbeat packet loss."
			::= { link18OBP 22 }

--  1.3.6.1.4.1.47477.10.21.18.3.23
		-- 1.3.6.1.4.1.47477.10.21.18.3.23
		link18_SwitchProtect OBJECT-TYPE
			SYNTAX INTEGER
				{
				off(0),
				on(1)
				}
			MAX-ACCESS read-write
			STATUS current
			DESCRIPTION
				"get or set the switch protection status of link18."
			::= { link18OBP 23 }
			
--  1.3.6.1.4.1.47477.10.21.18.3.24
		-- 1.3.6.1.4.1.47477.10.21.18.3.24
		link18_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link18OBP 24 }		

--  1.3.6.1.4.1.47477.10.21.18.3.25
		-- 1.3.6.1.4.1.47477.10.21.18.3.25
		link18_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link18OBP 25 }	

--  1.3.6.1.4.1.47477.10.21.18.3.26
		-- 1.3.6.1.4.1.47477.10.21.18.3.26
		link18_PowerAlarmStatus OBJECT-TYPE
			SYNTAX INTEGER
				{
				off(0),
				alarm(1),
				normal(2),
				na(3)
				}
			MAX-ACCESS read-only
			STATUS current
			DESCRIPTION
				"get whether a power alarm is generated."
			::= { link18OBP 26 }	


-- 1.3.6.1.4.1.47477.10.21.18.3.50.1
	link18_WorkModeChange 	OBJECT-TYPE    
    SYNTAX INTEGER	{
				manualMode(0),
				autoMode(1)
		}
	MAX-ACCESS read-only
	STATUS current
    DESCRIPTION
        "The Link mode Changed."
    ::= {link18OBPTrap 1}

-- 1.3.6.1.4.1.47477.10.21.18.3.50.2
	link18_StateChange 	OBJECT-TYPE    
    SYNTAX INTEGER	{
				bypass(0),
				primary(1)
		}
	MAX-ACCESS read-only
	STATUS current
    DESCRIPTION
        "The Link State(Channel) Changed."
    ::= {link18OBPTrap 2}

-- 1.3.6.1.4.1.47477.10.21.18.3.50.3
	link18_R1WaveSet 	OBJECT-TYPE    
    SYNTAX INTEGER	{
				w1310nm(0),
				w1550nm(1)
		}
	MAX-ACCESS read-only
	STATUS current
    DESCRIPTION
        "Set The link18 R1 Wave."
    ::= {link18OBPTrap 3}

-- 1.3.6.1.4.1.47477.10.21.18.3.50.4
	link18_R2WaveSet 	OBJECT-TYPE    
    SYNTAX INTEGER	{
				w1310nm(0),
				w1550nm(1)
		}
	MAX-ACCESS read-only
	STATUS current
    DESCRIPTION
        "Set The link18 R2 Wave."
    ::= {link18OBPTrap 4}			

-- 1.3.6.1.4.1.47477.10.21.18.3.50.5
	link18_R3WaveSet 	OBJECT-TYPE    
    SYNTAX INTEGER	{
				w1310nm(0),
				w1550nm(1)
		}
	MAX-ACCESS read-only
	STATUS current
    DESCRIPTION
        "Set The link18 R3 Wave."
    ::= {link18OBPTrap 5}

-- 1.3.6.1.4.1.47477.10.21.18.3.50.6
	link18_R4WaveSet 	OBJECT-TYPE    
    SYNTAX INTEGER	{
				w1310nm(0),
				w1550nm(1)
		}
	MAX-ACCESS read-only
	STATUS current
    DESCRIPTION
        "Set The link18 R4 Wave."
    ::= {link18OBPTrap 6}	
	
-- 1.3.6.1.4.1.47477.10.21.18.3.50.7
	link18_R1AlarmSet 	OBJECT-TYPE    
    SYNTAX DisplayString
	MAX-ACCESS read-only
	STATUS current
    DESCRIPTION
        "Set The link18 R1 Alarm Threshold."
    ::= {link18OBPTrap 7}

-- 1.3.6.1.4.1.47477.10.21.18.3.50.8
	link18_R2AlarmSet 	OBJECT-TYPE    
    SYNTAX DisplayString
	MAX-ACCESS read-only
	STATUS current
    DESCRIPTION
        "Set The link18 R2 Alarm Threshold."
    ::= {link18OBPTrap 8}
	
-- 1.3.6.1.4.1.47477.10.21.18.3.50.9
	link18_R3AlarmSet 	OBJECT-TYPE    
    SYNTAX DisplayString
	MAX-ACCESS read-only
	STATUS current
    DESCRIPTION
        "Set The link18 R3 Alarm Threshold."
    ::= {link18OBPTrap 9}

-- 1.3.6.1.4.1.47477.10.21.18.3.50.10
	link18_R4AlarmSet 	OBJECT-TYPE    
    SYNTAX DisplayString
	MAX-ACCESS read-only
	STATUS current
    DESCRIPTION
        "Set The link18 R4 Alarm Threshold."
    ::= {link18OBPTrap 10}	
	
	
-- 1.3.6.1.4.1.47477.10.21.18.3.50.11
	link18_1R1AlarmSet 	OBJECT-TYPE    
    SYNTAX DisplayString
	MAX-ACCESS read-only
	STATUS current
    DESCRIPTION
        "Set The link18 1R1 Alarm Threshold."
    ::= {link18OBPTrap 11}

-- 1.3.6.1.4.1.47477.10.21.18.3.50.12
	link18_2R1AlarmSet 	OBJECT-TYPE    
    SYNTAX DisplayString
	MAX-ACCESS read-only
	STATUS current
    DESCRIPTION
        "Set The link18 2R1 Alarm Threshold."
    ::= {link18OBPTrap 12}
	
-- 1.3.6.1.4.1.47477.10.21.18.3.50.13
	link18_1R2AlarmSet 	OBJECT-TYPE    
    SYNTAX DisplayString
	MAX-ACCESS read-only
	STATUS current
    DESCRIPTION
        "Set The link18 1R2 Alarm Threshold."
    ::= {link18OBPTrap 13}

-- 1.3.6.1.4.1.47477.10.21.18.3.50.14
	link18_2R2AlarmSet 	OBJECT-TYPE    
    SYNTAX DisplayString
	MAX-ACCESS read-only
	STATUS current
    DESCRIPTION
        "Set The link18 2R2 Alarm Threshold."
    ::= {link18OBPTrap 14}
	
-- 1.3.6.1.4.1.47477.10.21.18.3.50.15
	link18_1R3AlarmSet 	OBJECT-TYPE    
    SYNTAX DisplayString
	MAX-ACCESS read-only
	STATUS current
    DESCRIPTION
        "Set The link18 1R3 Alarm Threshold."
    ::= {link18OBPTrap 15}

-- 1.3.6.1.4.1.47477.10.21.18.3.50.16
	link18_2R3AlarmSet 	OBJECT-TYPE    
    SYNTAX DisplayString
	MAX-ACCESS read-only
	STATUS current
    DESCRIPTION
        "Set The link18 2R3 Alarm Threshold."
    ::= {link18OBPTrap 16}
	
-- 1.3.6.1.4.1.47477.10.21.18.3.50.17
	link18_1R4AlarmSet 	OBJECT-TYPE    
    SYNTAX DisplayString
	MAX-ACCESS read-only
	STATUS current
    DESCRIPTION
        "Set The link18 1R4 Alarm Threshold."
    ::= {link18OBPTrap 17}

-- 1.3.6.1.4.1.47477.10.21.18.3.50.18
	link18_2R4AlarmSet 	OBJECT-TYPE    
    SYNTAX DisplayString
	MAX-ACCESS read-only
	STATUS current
    DESCRIPTION
        "Set The link18 2R4 Alarm Threshold."
    ::= {link18OBPTrap 18}
	
-- 1.3.6.1.4.1.47477.10.21.18.3.50.19
	link18_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link18 PowerAlarmBypass2 Changed."
    ::= {link18OBPTrap 19}
	
-- 1.3.6.1.4.1.47477.10.21.18.3.50.20
	link18_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link18 PowerAlarmBypass4 Changed."
    ::= {link18OBPTrap 20}	
	
-- 1.3.6.1.4.1.47477.10.21.18.3.50.21
	link18_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link18 PowerAlarmBypass8 Changed."
    ::= {link18OBPTrap 21}
	
-- 1.3.6.1.4.1.47477.10.21.18.3.50.22
	link18_powerAlarmR1 	OBJECT-TYPE    
    SYNTAX DisplayString
	MAX-ACCESS read-only
	STATUS current
    DESCRIPTION
        "Set The link18 R1 Power Status Alarm."
    ::= {link18OBPTrap 22}
	
-- 1.3.6.1.4.1.47477.10.21.18.3.50.23
	link18_powerAlarmR2 	OBJECT-TYPE    
    SYNTAX DisplayString
	MAX-ACCESS read-only
	STATUS current
    DESCRIPTION
        "Set The link18 R2 Power Status Alarm."
    ::= {link18OBPTrap 23}
	
-- 1.3.6.1.4.1.47477.10.21.18.3.50.24
	link18_powerAlarmR3 	OBJECT-TYPE    
    SYNTAX DisplayString
	MAX-ACCESS read-only
	STATUS current
    DESCRIPTION
        "Set The link18 R3 Power Status Alarm."
    ::= {link18OBPTrap 24}
	
-- 1.3.6.1.4.1.47477.10.21.18.3.50.25
	link18_powerAlarmR4 	OBJECT-TYPE    
    SYNTAX DisplayString
	MAX-ACCESS read-only
	STATUS current
    DESCRIPTION
        "Set The link18 R4 Power Status Alarm."
    ::= {link18OBPTrap 25}
	
	
-- 1.3.6.1.4.1.47477.10.21.18.3.50.26
	link18_powerAlarm1R1 	OBJECT-TYPE    
    SYNTAX DisplayString
	MAX-ACCESS read-only
	STATUS current
    DESCRIPTION
        "Set The link18 1R1 Power Status Alarm."
    ::= {link18OBPTrap 26}
	
-- 1.3.6.1.4.1.47477.10.21.18.3.50.27
	link18_powerAlarm2R1 	OBJECT-TYPE    
    SYNTAX DisplayString
	MAX-ACCESS read-only
	STATUS current
    DESCRIPTION
        "Set The link18 2R1 Power Status Alarm."
    ::= {link18OBPTrap 27}
	
-- 1.3.6.1.4.1.47477.10.21.18.3.50.28
	link18_powerAlarm1R2 	OBJECT-TYPE    
    SYNTAX DisplayString
	MAX-ACCESS read-only
	STATUS current
    DESCRIPTION
        "Set The link18 1R2 Power Status Alarm."
    ::= {link18OBPTrap 28}
	
-- 1.3.6.1.4.1.47477.10.21.18.3.50.29
	link18_powerAlarm2R2 	OBJECT-TYPE    
    SYNTAX DisplayString
	MAX-ACCESS read-only
	STATUS current
    DESCRIPTION
        "Set The link18 2R2 Power Status Alarm."
    ::= {link18OBPTrap 29}
	
-- 1.3.6.1.4.1.47477.10.21.18.3.50.30
	link18_powerAlarm1R3 	OBJECT-TYPE    
    SYNTAX DisplayString
	MAX-ACCESS read-only
	STATUS current
    DESCRIPTION
        "Set The link18 1R3 Power Status Alarm."
    ::= {link18OBPTrap 30}
	
-- 1.3.6.1.4.1.47477.10.21.18.3.50.31
	link18_powerAlarm2R3 	OBJECT-TYPE    
    SYNTAX DisplayString
	MAX-ACCESS read-only
	STATUS current
    DESCRIPTION
        "Set The link18 2R1 Power Status Alarm."
    ::= {link18OBPTrap 31}
	
-- 1.3.6.1.4.1.47477.10.21.18.3.50.32
	link18_powerAlarm1R4 	OBJECT-TYPE    
    SYNTAX DisplayString
	MAX-ACCESS read-only
	STATUS current
    DESCRIPTION
        "Set The link18 1R4 Power Status Alarm."
    ::= {link18OBPTrap 32}
	
-- 1.3.6.1.4.1.47477.10.21.18.3.50.33
	link18_powerAlarm2R4 	OBJECT-TYPE    
    SYNTAX DisplayString
	MAX-ACCESS read-only
	STATUS current
    DESCRIPTION
        "Set The link18 2R4 Power Status Alarm."
    ::= {link18OBPTrap 33}
	
--  1.3.6.1.4.1.47477.10.21.19.3.1
		-- 1.3.6.1.4.1.47477.10.21.19.3.1
		link19_State OBJECT-TYPE
			SYNTAX INTEGER
				{
				off(0),
				on(1)
				}
			MAX-ACCESS read-only
			STATUS current
			DESCRIPTION
				"get the information about whether link19 is working."
			::= { link19OBP 1 }

		
--  1.3.6.1.4.1.47477.10.21.19.3.2
		-- 1.3.6.1.4.1.47477.10.21.19.3.2
		link19_DeviceType OBJECT-TYPE
			SYNTAX DisplayString
			MAX-ACCESS read-only
			STATUS current
			DESCRIPTION
				"get the type of card in link19."
			::= { link19OBP 2 }

			
--  1.3.6.1.4.1.47477.10.21.19.3.3
		-- 1.3.6.1.4.1.47477.10.21.19.3.3
		link19_WorkMode OBJECT-TYPE
			SYNTAX INTEGER
				{
				manualMode(0),
				autoMode(1)
				}
			MAX-ACCESS read-write
			STATUS current
			DESCRIPTION
				"get or set link19's work mode."
			::= { link19OBP 3 }

		
--  1.3.6.1.4.1.47477.10.21.19.3.4
		-- 1.3.6.1.4.1.47477.10.21.19.3.4
		link19_Channel OBJECT-TYPE
			SYNTAX INTEGER
				{
				bypass(0),
				primary(1)
				}
			MAX-ACCESS read-write
			STATUS current
			DESCRIPTION
				"get or set the channel in which link19 works."
			::= { link19OBP 4 }


--  1.3.6.1.4.1.47477.10.21.19.3.5
		-- 1.3.6.1.4.1.47477.10.21.19.3.5
		link19_R1Power OBJECT-TYPE
			SYNTAX DisplayString
			MAX-ACCESS read-only
			STATUS current
			DESCRIPTION
				"get the power of R1 in link19."
			::= { link19OBP 5 }

		
--  1.3.6.1.4.1.47477.10.21.19.3.6
		-- 1.3.6.1.4.1.47477.10.21.19.3.6
		link19_R2Power OBJECT-TYPE
			SYNTAX DisplayString
			MAX-ACCESS read-only
			STATUS current
			DESCRIPTION
				"get the power of R2 in link19."
			::= { link19OBP 6 }
			
--  1.3.6.1.4.1.47477.10.21.19.3.35
		-- 1.3.6.1.4.1.47477.10.21.19.3.35
		link19_R3Power OBJECT-TYPE
			SYNTAX DisplayString
			MAX-ACCESS read-only
			STATUS current
			DESCRIPTION
				"get the power of R3 in link19."
			::= { link19OBP 35 }
			
--  1.3.6.1.4.1.47477.10.21.19.3.36
		-- 1.3.6.1.4.1.47477.10.21.19.3.36
		link19_R4Power OBJECT-TYPE
			SYNTAX DisplayString
			MAX-ACCESS read-only
			STATUS current
			DESCRIPTION
				"get the power of R4 in link19."
			::= { link19OBP 36 }		
		
--  1.3.6.1.4.1.47477.10.21.19.3.7
		-- 1.3.6.1.4.1.47477.10.21.19.3.7
		link19_R1Wave OBJECT-TYPE
			SYNTAX INTEGER
				{
				w1310nm(0),
				w1550nm(1),
				na(2)
				}
			MAX-ACCESS read-write
			STATUS current
			DESCRIPTION
				"get or set the wave length of R1 in link19."
			::= { link19OBP 7 }

		
--  1.3.6.1.4.1.47477.10.21.19.3.8
		-- 1.3.6.1.4.1.47477.10.21.19.3.8
		link19_R2Wave OBJECT-TYPE
			SYNTAX INTEGER
				{
				w1310nm(0),
				w1550nm(1),
				na(2)
				}
			MAX-ACCESS read-write
			STATUS current
			DESCRIPTION
				"get or set the wave length of R2 in link19."
			::= { link19OBP 8 }


--  1.3.6.1.4.1.47477.10.21.19.3.27
		-- 1.3.6.1.4.1.47477.10.21.19.3.27
		link19_R3Wave OBJECT-TYPE
			SYNTAX INTEGER
				{
				w1310nm(0),
				w1550nm(1),
				na(2)
				}
			MAX-ACCESS read-write
			STATUS current
			DESCRIPTION
				"get or set the wave length of R3 in link19."
			::= { link19OBP 27 }

		
--  1.3.6.1.4.1.47477.10.21.19.3.28
		-- 1.3.6.1.4.1.47477.10.21.19.3.28
		link19_R4Wave OBJECT-TYPE
			SYNTAX INTEGER
				{
				w1310nm(0),
				w1550nm(1),
				na(2)
				}
			MAX-ACCESS read-write
			STATUS current
			DESCRIPTION
				"get or set the wave length of R4 in link19."
			::= { link19OBP 28 }
			
--  1.3.6.1.4.1.47477.10.21.19.3.9
		-- 1.3.6.1.4.1.47477.10.21.19.3.9
		link19_R1AlarmPower OBJECT-TYPE
			SYNTAX DisplayString
			MAX-ACCESS read-write
			STATUS current
			DESCRIPTION
				"get or set the power alarm threshold of R1 in link19."
			::= { link19OBP 9 }

		
--  1.3.6.1.4.1.47477.10.21.19.3.10
		-- 1.3.6.1.4.1.47477.10.21.19.3.10
		link19_R2AlarmPower OBJECT-TYPE
			SYNTAX DisplayString
			MAX-ACCESS read-write
			STATUS current
			DESCRIPTION
				"get or set the power alarm threshold of R2 in link19."
			::= { link19OBP 10 }


--  1.3.6.1.4.1.47477.10.21.19.3.29
		-- 1.3.6.1.4.1.47477.10.21.19.3.29
		link19_R3AlarmPower OBJECT-TYPE
			SYNTAX DisplayString
			MAX-ACCESS read-write
			STATUS current
			DESCRIPTION
				"get or set the power alarm threshold of R3 in link19."
			::= { link19OBP 29 }

		
--  1.3.6.1.4.1.47477.10.21.19.3.30
		-- 1.3.6.1.4.1.47477.10.21.19.3.30
		link19_R4AlarmPower OBJECT-TYPE
			SYNTAX DisplayString
			MAX-ACCESS read-write
			STATUS current
			DESCRIPTION
				"get or set the power alarm threshold of R4 in link19."
			::= { link19OBP 30 }

-- OBP4
--  1.3.6.1.4.1.47477.10.21.19.3.37
		-- 1.3.6.1.4.1.47477.10.21.19.3.37
		link19_1R1Power OBJECT-TYPE
			SYNTAX DisplayString
			MAX-ACCESS read-only
			STATUS current
			DESCRIPTION
				"get the power of 1R1 in link19."
			::= { link19OBP 37 }
			
--  1.3.6.1.4.1.47477.10.21.19.3.38
		-- 1.3.6.1.4.1.47477.10.21.19.3.38
		link19_1R2Power OBJECT-TYPE
			SYNTAX DisplayString
			MAX-ACCESS read-only
			STATUS current
			DESCRIPTION
				"get the power of 1R2 in link19."
			::= { link19OBP 38 }

--  1.3.6.1.4.1.47477.10.21.19.3.39
		-- 1.3.6.1.4.1.47477.10.21.19.3.39
		link19_1R3Power OBJECT-TYPE
			SYNTAX DisplayString
			MAX-ACCESS read-only
			STATUS current
			DESCRIPTION
				"get the power of 1R3 in link19."
			::= { link19OBP 39 }
			
--  1.3.6.1.4.1.47477.10.21.19.3.40
		-- 1.3.6.1.4.1.47477.10.21.19.3.40
		link19_1R4Power OBJECT-TYPE
			SYNTAX DisplayString
			MAX-ACCESS read-only
			STATUS current
			DESCRIPTION
				"get the power of 1R4 in link19."
			::= { link19OBP 40 }

--  1.3.6.1.4.1.47477.10.21.19.3.41
		-- 1.3.6.1.4.1.47477.10.21.19.3.41
		link19_2R1Power OBJECT-TYPE
			SYNTAX DisplayString
			MAX-ACCESS read-only
			STATUS current
			DESCRIPTION
				"get the power of 2R1 in link19."
			::= { link19OBP 41 }
			
--  1.3.6.1.4.1.47477.10.21.19.3.42
		-- 1.3.6.1.4.1.47477.10.21.19.3.42
		link19_2R2Power OBJECT-TYPE
			SYNTAX DisplayString
			MAX-ACCESS read-only
			STATUS current
			DESCRIPTION
				"get the power of 2R2 in link19."
			::= { link19OBP 42 }

--  1.3.6.1.4.1.47477.10.21.19.3.41
		-- 1.3.6.1.4.1.47477.10.21.19.3.43
		link19_2R3Power OBJECT-TYPE
			SYNTAX DisplayString
			MAX-ACCESS read-only
			STATUS current
			DESCRIPTION
				"get the power of 2R3 in link19."
			::= { link19OBP 43 }
			
--  1.3.6.1.4.1.47477.10.21.19.3.42
		-- 1.3.6.1.4.1.47477.10.21.19.3.44
		link19_2R4Power OBJECT-TYPE
			SYNTAX DisplayString
			MAX-ACCESS read-only
			STATUS current
			DESCRIPTION
				"get the power of 2R4 in link19."
			::= { link19OBP 44 }
			
--  1.3.6.1.4.1.47477.10.21.19.3.49
		-- 1.3.6.1.4.1.47477.10.21.19.3.49
		link19_1R1Wave OBJECT-TYPE
			SYNTAX INTEGER
				{
				w850nm(0),
				na(2)
				}
			MAX-ACCESS read-only
			STATUS current
			DESCRIPTION
				"get the wave length of 1R1 in link19."
			::= { link19OBP 49 }
		
--  1.3.6.1.4.1.47477.10.21.19.3.60
		-- 1.3.6.1.4.1.47477.10.21.19.3.60
		link19_1R2Wave OBJECT-TYPE
			SYNTAX INTEGER
				{
				w850nm(0),
				na(2)
				}
			MAX-ACCESS read-only
			STATUS current
			DESCRIPTION
				"get the wave length of 1R2 in link19."
			::= { link19OBP 60 }

--  1.3.6.1.4.1.47477.10.21.19.3.61
		-- 1.3.6.1.4.1.47477.10.21.19.3.61
		link19_1R3Wave OBJECT-TYPE
			SYNTAX INTEGER
				{
				w850nm(0),
				na(2)
				}
			MAX-ACCESS read-only
			STATUS current
			DESCRIPTION
				"get the wave length of 1R3 in link19."
			::= { link19OBP 61 }

		
--  1.3.6.1.4.1.47477.10.21.19.3.62
		-- 1.3.6.1.4.1.47477.10.21.19.3.62
		link19_1R4Wave OBJECT-TYPE
			SYNTAX INTEGER
				{
				w850nm(0),
				na(2)
				}
			MAX-ACCESS read-only
			STATUS current
			DESCRIPTION
				"get the wave length of 1R4 in link19."
			::= { link19OBP 62 }
	
--  1.3.6.1.4.1.47477.10.21.19.3.63
		-- 1.3.6.1.4.1.47477.10.21.19.3.63
		link19_2R1Wave OBJECT-TYPE
			SYNTAX INTEGER
				{
				w850nm(0),
				na(2)
				}
			MAX-ACCESS read-only
			STATUS current
			DESCRIPTION
				"get the wave length of 2R1 in link19."
			::= { link19OBP 63 }

		
--  1.3.6.1.4.1.47477.10.21.19.3.64
		-- 1.3.6.1.4.1.47477.10.21.19.3.64
		link19_2R2Wave OBJECT-TYPE
			SYNTAX INTEGER
				{
				w850nm(0),
				na(2)
				}
			MAX-ACCESS read-only
			STATUS current
			DESCRIPTION
				"get the wave length of 2R2 in link19."
			::= { link19OBP 64 }	
	
--  1.3.6.1.4.1.47477.10.21.19.3.65
		-- 1.3.6.1.4.1.47477.10.21.19.3.65
		link19_2R3Wave OBJECT-TYPE
			SYNTAX INTEGER
				{
				w850nm(0),
				na(2)
				}
			MAX-ACCESS read-only
			STATUS current
			DESCRIPTION
				"get the wave length of 2R3 in link19."
			::= { link19OBP 65 }

		
--  1.3.6.1.4.1.47477.10.21.19.3.66
		-- 1.3.6.1.4.1.47477.10.21.19.3.66
		link19_2R4Wave OBJECT-TYPE
			SYNTAX INTEGER
				{
				w850nm(0),
				na(2)
				}
			MAX-ACCESS read-only
			STATUS current
			DESCRIPTION
				"get the wave length of 2R4 in link19."
			::= { link19OBP 66 }	
			
--  1.3.6.1.4.1.47477.10.21.19.3.31
		-- 1.3.6.1.4.1.47477.10.21.19.3.31
		link19_1R1AlarmPower OBJECT-TYPE
			SYNTAX DisplayString
			MAX-ACCESS read-write
			STATUS current
			DESCRIPTION
				"get or set the power alarm threshold of 1R1 in link19."
			::= { link19OBP 31 }
			
--  1.3.6.1.4.1.47477.10.21.19.3.32
		-- 1.3.6.1.4.1.47477.10.21.19.3.32
		link19_1R2AlarmPower OBJECT-TYPE
			SYNTAX DisplayString
			MAX-ACCESS read-write
			STATUS current
			DESCRIPTION
				"get or set the power alarm threshold of 1R2 in link19."
			::= { link19OBP 32 }

--  1.3.6.1.4.1.47477.10.21.19.3.33
		-- 1.3.6.1.4.1.47477.10.21.19.3.33
		link19_1R3AlarmPower OBJECT-TYPE
			SYNTAX DisplayString
			MAX-ACCESS read-write
			STATUS current
			DESCRIPTION
				"get or set the power alarm threshold of 1R3 in link19."
			::= { link19OBP 33 }
			
--  1.3.6.1.4.1.47477.10.21.19.3.34
		-- 1.3.6.1.4.1.47477.10.21.19.3.34
		link19_1R4AlarmPower OBJECT-TYPE
			SYNTAX DisplayString
			MAX-ACCESS read-write
			STATUS current
			DESCRIPTION
				"get or set the power alarm threshold of 1R4 in link19."
			::= { link19OBP 34 }

--  1.3.6.1.4.1.47477.10.21.19.3.45
		-- 1.3.6.1.4.1.47477.10.21.19.3.45
		link19_2R1AlarmPower OBJECT-TYPE
			SYNTAX DisplayString
			MAX-ACCESS read-write
			STATUS current
			DESCRIPTION
				"get or set the power alarm threshold of 2R1 in link19."
			::= { link19OBP 45 }
			
--  1.3.6.1.4.1.47477.10.21.19.3.46
		-- 1.3.6.1.4.1.47477.10.21.19.3.46
		link19_2R2AlarmPower OBJECT-TYPE
			SYNTAX DisplayString
			MAX-ACCESS read-write
			STATUS current
			DESCRIPTION
				"get or set the power alarm threshold of 2R2 in link19."
			::= { link19OBP 46 }

--  1.3.6.1.4.1.47477.10.21.19.3.47
		-- 1.3.6.1.4.1.47477.10.21.19.3.47
		link19_2R3AlarmPower OBJECT-TYPE
			SYNTAX DisplayString
			MAX-ACCESS read-write
			STATUS current
			DESCRIPTION
				"get or set the power alarm threshold of 2R3 in link19."
			::= { link19OBP 47 }
			
--  1.3.6.1.4.1.47477.10.21.19.3.48
		-- 1.3.6.1.4.1.47477.10.21.19.3.48
		link19_2R4AlarmPower OBJECT-TYPE
			SYNTAX DisplayString
			MAX-ACCESS read-write
			STATUS current
			DESCRIPTION
				"get or set the power alarm threshold of 2R4 in link19."
			::= { link19OBP 48 }
			
--  1.3.6.1.4.1.47477.10.21.19.3.11
		-- 1.3.6.1.4.1.47477.10.21.19.3.11
		link19_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link19OBP 11 }
			
--  1.3.6.1.4.1.47477.10.21.19.3.67
		-- 1.3.6.1.4.1.47477.10.21.19.3.67
		link19_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link19OBP 67 }
			
--  1.3.6.1.4.1.47477.10.21.19.3.68
		-- 1.3.6.1.4.1.47477.10.21.19.3.68
		link19_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link19OBP 68 }
			
--  1.3.6.1.4.1.47477.10.21.19.3.12
		-- 1.3.6.1.4.1.47477.10.21.19.3.12
		link19_ReturnDelay OBJECT-TYPE
			--SYNTAX Integer32
			SYNTAX Integer32
			MAX-ACCESS read-write
			STATUS current
			DESCRIPTION
				"get or set how long link19 takes to return to automatic mode."
			::= { link19OBP 12 }
			
--  1.3.6.1.4.1.47477.10.21.19.3.13
		-- 1.3.6.1.4.1.47477.10.21.19.3.13
		link19_BackMode OBJECT-TYPE
			SYNTAX INTEGER
				{
				autoNoBack(0),
				autoBack(1)
				}
			MAX-ACCESS read-write
			STATUS current
			DESCRIPTION
				"get or set the back mode of link19."
			::= { link19OBP 13 }

		
--  1.3.6.1.4.1.47477.10.21.19.3.14
		-- 1.3.6.1.4.1.47477.10.21.19.3.14
		link19_BackDelay OBJECT-TYPE
			SYNTAX Integer32
			MAX-ACCESS read-write
			STATUS current
			DESCRIPTION
				"get or set the back delay."
			::= { link19OBP 14 }

--  1.3.6.1.4.1.47477.10.21.19.3.15
		-- 1.3.6.1.4.1.47477.10.21.19.3.15
		link19_ActiveHeartSwitch OBJECT-TYPE
			SYNTAX INTEGER
				{
				off(0),
				on(1)
				}
			MAX-ACCESS read-write
			STATUS current
			DESCRIPTION
				"get or set the switch status of active heartbeat."
			::= { link19OBP 15 }

		
--  1.3.6.1.4.1.47477.10.21.19.3.16
		-- 1.3.6.1.4.1.47477.10.21.19.3.16
		link19_ActiveSendInterval OBJECT-TYPE
			SYNTAX Integer32
			MAX-ACCESS read-write
			STATUS current
			DESCRIPTION
				"get or set the send interval of active heartbeat."
			::= { link19OBP 16 }		

--  1.3.6.1.4.1.47477.10.21.19.3.17
		-- 1.3.6.1.4.1.47477.10.21.19.3.17
		link19_ActiveTimeOut OBJECT-TYPE
			SYNTAX Integer32
			MAX-ACCESS read-write
			STATUS current
			DESCRIPTION
				"get or set how long the active heartbeat send timeout."
			::= { link19OBP 17 }

--  1.3.6.1.4.1.47477.10.21.19.3.18
		-- 1.3.6.1.4.1.47477.10.21.19.3.18
		link19_ActiveLossBypass OBJECT-TYPE
			SYNTAX Integer32
			MAX-ACCESS read-write
			STATUS current
			DESCRIPTION
				"get or set the bypass for active heartbeat packet loss."
			::= { link19OBP 18 }

--  1.3.6.1.4.1.47477.10.21.19.3.19
		-- 1.3.6.1.4.1.47477.10.21.19.3.19
		link19_PingIpAddress OBJECT-TYPE
			SYNTAX IpAddress
			MAX-ACCESS read-write
			STATUS current
			DESCRIPTION
				"get or set the ping ip address of link19."
			::= { link19OBP 19 }

--  1.3.6.1.4.1.47477.10.21.19.3.20
		-- 1.3.6.1.4.1.47477.10.21.19.3.20
		link19_PassiveHeartSwitch OBJECT-TYPE
			SYNTAX INTEGER
				{
				off(0),
				on(1)
				}
			MAX-ACCESS read-write
			STATUS current
			DESCRIPTION
				"get or set the switch status of passive heartbeat."
			::= { link19OBP 20 }
	

--  1.3.6.1.4.1.47477.10.21.19.3.21
		-- 1.3.6.1.4.1.47477.10.21.19.3.21
		link19_PassiveTimeOut OBJECT-TYPE
			SYNTAX Integer32
			MAX-ACCESS read-write
			STATUS current
			DESCRIPTION
				"get or set how long the passive heartbeat send timeout."
			::= { link19OBP 21 }

--  1.3.6.1.4.1.47477.10.21.19.3.22
		-- 1.3.6.1.4.1.47477.10.21.19.3.22
		link19_PassiveLossBypass OBJECT-TYPE
			SYNTAX Integer32
			MAX-ACCESS read-write
			STATUS current
			DESCRIPTION
				"get or set the bypass for passive heartbeat packet loss."
			::= { link19OBP 22 }

--  1.3.6.1.4.1.47477.10.21.19.3.23
		-- 1.3.6.1.4.1.47477.10.21.19.3.23
		link19_SwitchProtect OBJECT-TYPE
			SYNTAX INTEGER
				{
				off(0),
				on(1)
				}
			MAX-ACCESS read-write
			STATUS current
			DESCRIPTION
				"get or set the switch protection status of link19."
			::= { link19OBP 23 }
			
--  1.3.6.1.4.1.47477.10.21.19.3.24
		-- 1.3.6.1.4.1.47477.10.21.19.3.24
		link19_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link19OBP 24 }		

--  1.3.6.1.4.1.47477.10.21.19.3.25
		-- 1.3.6.1.4.1.47477.10.21.19.3.25
		link19_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link19OBP 25 }	

--  1.3.6.1.4.1.47477.10.21.19.3.26
		-- 1.3.6.1.4.1.47477.10.21.19.3.26
		link19_PowerAlarmStatus OBJECT-TYPE
			SYNTAX INTEGER
				{
				off(0),
				alarm(1),
				normal(2),
				na(3)
				}
			MAX-ACCESS read-only
			STATUS current
			DESCRIPTION
				"get whether a power alarm is generated."
			::= { link19OBP 26 }	


-- 1.3.6.1.4.1.47477.10.21.19.3.50.1
	link19_WorkModeChange 	OBJECT-TYPE    
    SYNTAX INTEGER	{
				manualMode(0),
				autoMode(1)
		}
	MAX-ACCESS read-only
	STATUS current
    DESCRIPTION
        "The Link mode Changed."
    ::= {link19OBPTrap 1}

-- 1.3.6.1.4.1.47477.10.21.19.3.50.2
	link19_StateChange 	OBJECT-TYPE    
    SYNTAX INTEGER	{
				bypass(0),
				primary(1)
		}
	MAX-ACCESS read-only
	STATUS current
    DESCRIPTION
        "The Link State(Channel) Changed."
    ::= {link19OBPTrap 2}

-- 1.3.6.1.4.1.47477.10.21.19.3.50.3
	link19_R1WaveSet 	OBJECT-TYPE    
    SYNTAX INTEGER	{
				w1310nm(0),
				w1550nm(1)
		}
	MAX-ACCESS read-only
	STATUS current
    DESCRIPTION
        "Set The link19 R1 Wave."
    ::= {link19OBPTrap 3}

-- 1.3.6.1.4.1.47477.10.21.19.3.50.4
	link19_R2WaveSet 	OBJECT-TYPE    
    SYNTAX INTEGER	{
				w1310nm(0),
				w1550nm(1)
		}
	MAX-ACCESS read-only
	STATUS current
    DESCRIPTION
        "Set The link19 R2 Wave."
    ::= {link19OBPTrap 4}			

-- 1.3.6.1.4.1.47477.10.21.19.3.50.5
	link19_R3WaveSet 	OBJECT-TYPE    
    SYNTAX INTEGER	{
				w1310nm(0),
				w1550nm(1)
		}
	MAX-ACCESS read-only
	STATUS current
    DESCRIPTION
        "Set The link19 R3 Wave."
    ::= {link19OBPTrap 5}

-- 1.3.6.1.4.1.47477.10.21.19.3.50.6
	link19_R4WaveSet 	OBJECT-TYPE    
    SYNTAX INTEGER	{
				w1310nm(0),
				w1550nm(1)
		}
	MAX-ACCESS read-only
	STATUS current
    DESCRIPTION
        "Set The link19 R4 Wave."
    ::= {link19OBPTrap 6}	
	
-- 1.3.6.1.4.1.47477.10.21.19.3.50.7
	link19_R1AlarmSet 	OBJECT-TYPE    
    SYNTAX DisplayString
	MAX-ACCESS read-only
	STATUS current
    DESCRIPTION
        "Set The link19 R1 Alarm Threshold."
    ::= {link19OBPTrap 7}

-- 1.3.6.1.4.1.47477.10.21.19.3.50.8
	link19_R2AlarmSet 	OBJECT-TYPE    
    SYNTAX DisplayString
	MAX-ACCESS read-only
	STATUS current
    DESCRIPTION
        "Set The link19 R2 Alarm Threshold."
    ::= {link19OBPTrap 8}
	
-- 1.3.6.1.4.1.47477.10.21.19.3.50.9
	link19_R3AlarmSet 	OBJECT-TYPE    
    SYNTAX DisplayString
	MAX-ACCESS read-only
	STATUS current
    DESCRIPTION
        "Set The link19 R3 Alarm Threshold."
    ::= {link19OBPTrap 9}

-- 1.3.6.1.4.1.47477.10.21.19.3.50.10
	link19_R4AlarmSet 	OBJECT-TYPE    
    SYNTAX DisplayString
	MAX-ACCESS read-only
	STATUS current
    DESCRIPTION
        "Set The link19 R4 Alarm Threshold."
    ::= {link19OBPTrap 10}	
	
	
-- 1.3.6.1.4.1.47477.10.21.19.3.50.11
	link19_1R1AlarmSet 	OBJECT-TYPE    
    SYNTAX DisplayString
	MAX-ACCESS read-only
	STATUS current
    DESCRIPTION
        "Set The link19 1R1 Alarm Threshold."
    ::= {link19OBPTrap 11}

-- 1.3.6.1.4.1.47477.10.21.19.3.50.12
	link19_2R1AlarmSet 	OBJECT-TYPE    
    SYNTAX DisplayString
	MAX-ACCESS read-only
	STATUS current
    DESCRIPTION
        "Set The link19 2R1 Alarm Threshold."
    ::= {link19OBPTrap 12}
	
-- 1.3.6.1.4.1.47477.10.21.19.3.50.13
	link19_1R2AlarmSet 	OBJECT-TYPE    
    SYNTAX DisplayString
	MAX-ACCESS read-only
	STATUS current
    DESCRIPTION
        "Set The link19 1R2 Alarm Threshold."
    ::= {link19OBPTrap 13}

-- 1.3.6.1.4.1.47477.10.21.19.3.50.14
	link19_2R2AlarmSet 	OBJECT-TYPE    
    SYNTAX DisplayString
	MAX-ACCESS read-only
	STATUS current
    DESCRIPTION
        "Set The link19 2R2 Alarm Threshold."
    ::= {link19OBPTrap 14}
	
-- 1.3.6.1.4.1.47477.10.21.19.3.50.15
	link19_1R3AlarmSet 	OBJECT-TYPE    
    SYNTAX DisplayString
	MAX-ACCESS read-only
	STATUS current
    DESCRIPTION
        "Set The link19 1R3 Alarm Threshold."
    ::= {link19OBPTrap 15}

-- 1.3.6.1.4.1.47477.10.21.19.3.50.16
	link19_2R3AlarmSet 	OBJECT-TYPE    
    SYNTAX DisplayString
	MAX-ACCESS read-only
	STATUS current
    DESCRIPTION
        "Set The link19 2R3 Alarm Threshold."
    ::= {link19OBPTrap 16}
	
-- 1.3.6.1.4.1.47477.10.21.19.3.50.17
	link19_1R4AlarmSet 	OBJECT-TYPE    
    SYNTAX DisplayString
	MAX-ACCESS read-only
	STATUS current
    DESCRIPTION
        "Set The link19 1R4 Alarm Threshold."
    ::= {link19OBPTrap 17}

-- 1.3.6.1.4.1.47477.10.21.19.3.50.18
	link19_2R4AlarmSet 	OBJECT-TYPE    
    SYNTAX DisplayString
	MAX-ACCESS read-only
	STATUS current
    DESCRIPTION
        "Set The link19 2R4 Alarm Threshold."
    ::= {link19OBPTrap 18}
	
-- 1.3.6.1.4.1.47477.10.21.19.3.50.19
	link19_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link19 PowerAlarmBypass2 Changed."
    ::= {link19OBPTrap 19}
	
-- 1.3.6.1.4.1.47477.10.21.19.3.50.20
	link19_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link19 PowerAlarmBypass4 Changed."
    ::= {link19OBPTrap 20}	
	
-- 1.3.6.1.4.1.47477.10.21.19.3.50.21
	link19_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link19 PowerAlarmBypass8 Changed."
    ::= {link19OBPTrap 21}
	
-- 1.3.6.1.4.1.47477.10.21.19.3.50.22
	link19_powerAlarmR1 	OBJECT-TYPE    
    SYNTAX DisplayString
	MAX-ACCESS read-only
	STATUS current
    DESCRIPTION
        "Set The link19 R1 Power Status Alarm."
    ::= {link19OBPTrap 22}
	
-- 1.3.6.1.4.1.47477.10.21.19.3.50.23
	link19_powerAlarmR2 	OBJECT-TYPE    
    SYNTAX DisplayString
	MAX-ACCESS read-only
	STATUS current
    DESCRIPTION
        "Set The link19 R2 Power Status Alarm."
    ::= {link19OBPTrap 23}
	
-- 1.3.6.1.4.1.47477.10.21.19.3.50.24
	link19_powerAlarmR3 	OBJECT-TYPE    
    SYNTAX DisplayString
	MAX-ACCESS read-only
	STATUS current
    DESCRIPTION
        "Set The link19 R3 Power Status Alarm."
    ::= {link19OBPTrap 24}
	
-- 1.3.6.1.4.1.47477.10.21.19.3.50.25
	link19_powerAlarmR4 	OBJECT-TYPE    
    SYNTAX DisplayString
	MAX-ACCESS read-only
	STATUS current
    DESCRIPTION
        "Set The link19 R4 Power Status Alarm."
    ::= {link19OBPTrap 25}
	
	
-- 1.3.6.1.4.1.47477.10.21.19.3.50.26
	link19_powerAlarm1R1 	OBJECT-TYPE    
    SYNTAX DisplayString
	MAX-ACCESS read-only
	STATUS current
    DESCRIPTION
        "Set The link19 1R1 Power Status Alarm."
    ::= {link19OBPTrap 26}
	
-- 1.3.6.1.4.1.47477.10.21.19.3.50.27
	link19_powerAlarm2R1 	OBJECT-TYPE    
    SYNTAX DisplayString
	MAX-ACCESS read-only
	STATUS current
    DESCRIPTION
        "Set The link19 2R1 Power Status Alarm."
    ::= {link19OBPTrap 27}
	
-- 1.3.6.1.4.1.47477.10.21.19.3.50.28
	link19_powerAlarm1R2 	OBJECT-TYPE    
    SYNTAX DisplayString
	MAX-ACCESS read-only
	STATUS current
    DESCRIPTION
        "Set The link19 1R2 Power Status Alarm."
    ::= {link19OBPTrap 28}
	
-- 1.3.6.1.4.1.47477.10.21.19.3.50.29
	link19_powerAlarm2R2 	OBJECT-TYPE    
    SYNTAX DisplayString
	MAX-ACCESS read-only
	STATUS current
    DESCRIPTION
        "Set The link19 2R2 Power Status Alarm."
    ::= {link19OBPTrap 29}
	
-- 1.3.6.1.4.1.47477.10.21.19.3.50.30
	link19_powerAlarm1R3 	OBJECT-TYPE    
    SYNTAX DisplayString
	MAX-ACCESS read-only
	STATUS current
    DESCRIPTION
        "Set The link19 1R3 Power Status Alarm."
    ::= {link19OBPTrap 30}
	
-- 1.3.6.1.4.1.47477.10.21.19.3.50.31
	link19_powerAlarm2R3 	OBJECT-TYPE    
    SYNTAX DisplayString
	MAX-ACCESS read-only
	STATUS current
    DESCRIPTION
        "Set The link19 2R1 Power Status Alarm."
    ::= {link19OBPTrap 31}
	
-- 1.3.6.1.4.1.47477.10.21.19.3.50.32
	link19_powerAlarm1R4 	OBJECT-TYPE    
    SYNTAX DisplayString
	MAX-ACCESS read-only
	STATUS current
    DESCRIPTION
        "Set The link19 1R4 Power Status Alarm."
    ::= {link19OBPTrap 32}
	
-- 1.3.6.1.4.1.47477.10.21.19.3.50.33
	link19_powerAlarm2R4 	OBJECT-TYPE    
    SYNTAX DisplayString
	MAX-ACCESS read-only
	STATUS current
    DESCRIPTION
        "Set The link19 2R4 Power Status Alarm."
    ::= {link19OBPTrap 33}
	
--  1.3.6.1.4.1.47477.10.21.20.3.1
		-- 1.3.6.1.4.1.47477.10.21.20.3.1
		link20_State OBJECT-TYPE
			SYNTAX INTEGER
				{
				off(0),
				on(1)
				}
			MAX-ACCESS read-only
			STATUS current
			DESCRIPTION
				"get the information about whether link20 is working."
			::= { link20OBP 1 }

		
--  1.3.6.1.4.1.47477.10.21.20.3.2
		-- 1.3.6.1.4.1.47477.10.21.20.3.2
		link20_DeviceType OBJECT-TYPE
			SYNTAX DisplayString
			MAX-ACCESS read-only
			STATUS current
			DESCRIPTION
				"get the type of card in link20."
			::= { link20OBP 2 }

			
--  1.3.6.1.4.1.47477.10.21.20.3.3
		-- 1.3.6.1.4.1.47477.10.21.20.3.3
		link20_WorkMode OBJECT-TYPE
			SYNTAX INTEGER
				{
				manualMode(0),
				autoMode(1)
				}
			MAX-ACCESS read-write
			STATUS current
			DESCRIPTION
				"get or set link20's work mode."
			::= { link20OBP 3 }

		
--  1.3.6.1.4.1.47477.10.21.20.3.4
		-- 1.3.6.1.4.1.47477.10.21.20.3.4
		link20_Channel OBJECT-TYPE
			SYNTAX INTEGER
				{
				bypass(0),
				primary(1)
				}
			MAX-ACCESS read-write
			STATUS current
			DESCRIPTION
				"get or set the channel in which link20 works."
			::= { link20OBP 4 }


--  1.3.6.1.4.1.47477.10.21.20.3.5
		-- 1.3.6.1.4.1.47477.10.21.20.3.5
		link20_R1Power OBJECT-TYPE
			SYNTAX DisplayString
			MAX-ACCESS read-only
			STATUS current
			DESCRIPTION
				"get the power of R1 in link20."
			::= { link20OBP 5 }

		
--  1.3.6.1.4.1.47477.10.21.20.3.6
		-- 1.3.6.1.4.1.47477.10.21.20.3.6
		link20_R2Power OBJECT-TYPE
			SYNTAX DisplayString
			MAX-ACCESS read-only
			STATUS current
			DESCRIPTION
				"get the power of R2 in link20."
			::= { link20OBP 6 }
			
--  1.3.6.1.4.1.47477.10.21.20.3.35
		-- 1.3.6.1.4.1.47477.10.21.20.3.35
		link20_R3Power OBJECT-TYPE
			SYNTAX DisplayString
			MAX-ACCESS read-only
			STATUS current
			DESCRIPTION
				"get the power of R3 in link20."
			::= { link20OBP 35 }
			
--  1.3.6.1.4.1.47477.10.21.20.3.36
		-- 1.3.6.1.4.1.47477.10.21.20.3.36
		link20_R4Power OBJECT-TYPE
			SYNTAX DisplayString
			MAX-ACCESS read-only
			STATUS current
			DESCRIPTION
				"get the power of R4 in link20."
			::= { link20OBP 36 }		
		
--  1.3.6.1.4.1.47477.10.21.20.3.7
		-- 1.3.6.1.4.1.47477.10.21.20.3.7
		link20_R1Wave OBJECT-TYPE
			SYNTAX INTEGER
				{
				w1310nm(0),
				w1550nm(1),
				na(2)
				}
			MAX-ACCESS read-write
			STATUS current
			DESCRIPTION
				"get or set the wave length of R1 in link20."
			::= { link20OBP 7 }

		
--  1.3.6.1.4.1.47477.10.21.20.3.8
		-- 1.3.6.1.4.1.47477.10.21.20.3.8
		link20_R2Wave OBJECT-TYPE
			SYNTAX INTEGER
				{
				w1310nm(0),
				w1550nm(1),
				na(2)
				}
			MAX-ACCESS read-write
			STATUS current
			DESCRIPTION
				"get or set the wave length of R2 in link20."
			::= { link20OBP 8 }


--  1.3.6.1.4.1.47477.10.21.20.3.27
		-- 1.3.6.1.4.1.47477.10.21.20.3.27
		link20_R3Wave OBJECT-TYPE
			SYNTAX INTEGER
				{
				w1310nm(0),
				w1550nm(1),
				na(2)
				}
			MAX-ACCESS read-write
			STATUS current
			DESCRIPTION
				"get or set the wave length of R3 in link20."
			::= { link20OBP 27 }

		
--  1.3.6.1.4.1.47477.10.21.20.3.28
		-- 1.3.6.1.4.1.47477.10.21.20.3.28
		link20_R4Wave OBJECT-TYPE
			SYNTAX INTEGER
				{
				w1310nm(0),
				w1550nm(1),
				na(2)
				}
			MAX-ACCESS read-write
			STATUS current
			DESCRIPTION
				"get or set the wave length of R4 in link20."
			::= { link20OBP 28 }
			
--  1.3.6.1.4.1.47477.10.21.20.3.9
		-- 1.3.6.1.4.1.47477.10.21.20.3.9
		link20_R1AlarmPower OBJECT-TYPE
			SYNTAX DisplayString
			MAX-ACCESS read-write
			STATUS current
			DESCRIPTION
				"get or set the power alarm threshold of R1 in link20."
			::= { link20OBP 9 }

		
--  1.3.6.1.4.1.47477.10.21.20.3.10
		-- 1.3.6.1.4.1.47477.10.21.20.3.10
		link20_R2AlarmPower OBJECT-TYPE
			SYNTAX DisplayString
			MAX-ACCESS read-write
			STATUS current
			DESCRIPTION
				"get or set the power alarm threshold of R2 in link20."
			::= { link20OBP 10 }


--  1.3.6.1.4.1.47477.10.21.20.3.29
		-- 1.3.6.1.4.1.47477.10.21.20.3.29
		link20_R3AlarmPower OBJECT-TYPE
			SYNTAX DisplayString
			MAX-ACCESS read-write
			STATUS current
			DESCRIPTION
				"get or set the power alarm threshold of R3 in link20."
			::= { link20OBP 29 }

		
--  1.3.6.1.4.1.47477.10.21.20.3.30
		-- 1.3.6.1.4.1.47477.10.21.20.3.30
		link20_R4AlarmPower OBJECT-TYPE
			SYNTAX DisplayString
			MAX-ACCESS read-write
			STATUS current
			DESCRIPTION
				"get or set the power alarm threshold of R4 in link20."
			::= { link20OBP 30 }

-- OBP4
--  1.3.6.1.4.1.47477.10.21.20.3.37
		-- 1.3.6.1.4.1.47477.10.21.20.3.37
		link20_1R1Power OBJECT-TYPE
			SYNTAX DisplayString
			MAX-ACCESS read-only
			STATUS current
			DESCRIPTION
				"get the power of 1R1 in link20."
			::= { link20OBP 37 }
			
--  1.3.6.1.4.1.47477.10.21.20.3.38
		-- 1.3.6.1.4.1.47477.10.21.20.3.38
		link20_1R2Power OBJECT-TYPE
			SYNTAX DisplayString
			MAX-ACCESS read-only
			STATUS current
			DESCRIPTION
				"get the power of 1R2 in link20."
			::= { link20OBP 38 }

--  1.3.6.1.4.1.47477.10.21.20.3.39
		-- 1.3.6.1.4.1.47477.10.21.20.3.39
		link20_1R3Power OBJECT-TYPE
			SYNTAX DisplayString
			MAX-ACCESS read-only
			STATUS current
			DESCRIPTION
				"get the power of 1R3 in link20."
			::= { link20OBP 39 }
			
--  1.3.6.1.4.1.47477.10.21.20.3.40
		-- 1.3.6.1.4.1.47477.10.21.20.3.40
		link20_1R4Power OBJECT-TYPE
			SYNTAX DisplayString
			MAX-ACCESS read-only
			STATUS current
			DESCRIPTION
				"get the power of 1R4 in link20."
			::= { link20OBP 40 }

--  1.3.6.1.4.1.47477.10.21.20.3.41
		-- 1.3.6.1.4.1.47477.10.21.20.3.41
		link20_2R1Power OBJECT-TYPE
			SYNTAX DisplayString
			MAX-ACCESS read-only
			STATUS current
			DESCRIPTION
				"get the power of 2R1 in link20."
			::= { link20OBP 41 }
			
--  1.3.6.1.4.1.47477.10.21.20.3.42
		-- 1.3.6.1.4.1.47477.10.21.20.3.42
		link20_2R2Power OBJECT-TYPE
			SYNTAX DisplayString
			MAX-ACCESS read-only
			STATUS current
			DESCRIPTION
				"get the power of 2R2 in link20."
			::= { link20OBP 42 }

--  1.3.6.1.4.1.47477.10.21.20.3.41
		-- 1.3.6.1.4.1.47477.10.21.20.3.43
		link20_2R3Power OBJECT-TYPE
			SYNTAX DisplayString
			MAX-ACCESS read-only
			STATUS current
			DESCRIPTION
				"get the power of 2R3 in link20."
			::= { link20OBP 43 }
			
--  1.3.6.1.4.1.47477.10.21.20.3.42
		-- 1.3.6.1.4.1.47477.10.21.20.3.44
		link20_2R4Power OBJECT-TYPE
			SYNTAX DisplayString
			MAX-ACCESS read-only
			STATUS current
			DESCRIPTION
				"get the power of 2R4 in link20."
			::= { link20OBP 44 }
			
--  1.3.6.1.4.1.47477.10.21.20.3.49
		-- 1.3.6.1.4.1.47477.10.21.20.3.49
		link20_1R1Wave OBJECT-TYPE
			SYNTAX INTEGER
				{
				w850nm(0),
				na(2)
				}
			MAX-ACCESS read-only
			STATUS current
			DESCRIPTION
				"get the wave length of 1R1 in link20."
			::= { link20OBP 49 }
		
--  1.3.6.1.4.1.47477.10.21.20.3.60
		-- 1.3.6.1.4.1.47477.10.21.20.3.60
		link20_1R2Wave OBJECT-TYPE
			SYNTAX INTEGER
				{
				w850nm(0),
				na(2)
				}
			MAX-ACCESS read-only
			STATUS current
			DESCRIPTION
				"get the wave length of 1R2 in link20."
			::= { link20OBP 60 }

--  1.3.6.1.4.1.47477.10.21.20.3.61
		-- 1.3.6.1.4.1.47477.10.21.20.3.61
		link20_1R3Wave OBJECT-TYPE
			SYNTAX INTEGER
				{
				w850nm(0),
				na(2)
				}
			MAX-ACCESS read-only
			STATUS current
			DESCRIPTION
				"get the wave length of 1R3 in link20."
			::= { link20OBP 61 }

		
--  1.3.6.1.4.1.47477.10.21.20.3.62
		-- 1.3.6.1.4.1.47477.10.21.20.3.62
		link20_1R4Wave OBJECT-TYPE
			SYNTAX INTEGER
				{
				w850nm(0),
				na(2)
				}
			MAX-ACCESS read-only
			STATUS current
			DESCRIPTION
				"get the wave length of 1R4 in link20."
			::= { link20OBP 62 }
	
--  1.3.6.1.4.1.47477.10.21.20.3.63
		-- 1.3.6.1.4.1.47477.10.21.20.3.63
		link20_2R1Wave OBJECT-TYPE
			SYNTAX INTEGER
				{
				w850nm(0),
				na(2)
				}
			MAX-ACCESS read-only
			STATUS current
			DESCRIPTION
				"get the wave length of 2R1 in link20."
			::= { link20OBP 63 }

		
--  1.3.6.1.4.1.47477.10.21.20.3.64
		-- 1.3.6.1.4.1.47477.10.21.20.3.64
		link20_2R2Wave OBJECT-TYPE
			SYNTAX INTEGER
				{
				w850nm(0),
				na(2)
				}
			MAX-ACCESS read-only
			STATUS current
			DESCRIPTION
				"get the wave length of 2R2 in link20."
			::= { link20OBP 64 }	
	
--  1.3.6.1.4.1.47477.10.21.20.3.65
		-- 1.3.6.1.4.1.47477.10.21.20.3.65
		link20_2R3Wave OBJECT-TYPE
			SYNTAX INTEGER
				{
				w850nm(0),
				na(2)
				}
			MAX-ACCESS read-only
			STATUS current
			DESCRIPTION
				"get the wave length of 2R3 in link20."
			::= { link20OBP 65 }

		
--  1.3.6.1.4.1.47477.10.21.20.3.66
		-- 1.3.6.1.4.1.47477.10.21.20.3.66
		link20_2R4Wave OBJECT-TYPE
			SYNTAX INTEGER
				{
				w850nm(0),
				na(2)
				}
			MAX-ACCESS read-only
			STATUS current
			DESCRIPTION
				"get the wave length of 2R4 in link20."
			::= { link20OBP 66 }	
			
--  1.3.6.1.4.1.47477.10.21.20.3.31
		-- 1.3.6.1.4.1.47477.10.21.20.3.31
		link20_1R1AlarmPower OBJECT-TYPE
			SYNTAX DisplayString
			MAX-ACCESS read-write
			STATUS current
			DESCRIPTION
				"get or set the power alarm threshold of 1R1 in link20."
			::= { link20OBP 31 }
			
--  1.3.6.1.4.1.47477.10.21.20.3.32
		-- 1.3.6.1.4.1.47477.10.21.20.3.32
		link20_1R2AlarmPower OBJECT-TYPE
			SYNTAX DisplayString
			MAX-ACCESS read-write
			STATUS current
			DESCRIPTION
				"get or set the power alarm threshold of 1R2 in link20."
			::= { link20OBP 32 }

--  1.3.6.1.4.1.47477.10.21.20.3.33
		-- 1.3.6.1.4.1.47477.10.21.20.3.33
		link20_1R3AlarmPower OBJECT-TYPE
			SYNTAX DisplayString
			MAX-ACCESS read-write
			STATUS current
			DESCRIPTION
				"get or set the power alarm threshold of 1R3 in link20."
			::= { link20OBP 33 }
			
--  1.3.6.1.4.1.47477.10.21.20.3.34
		-- 1.3.6.1.4.1.47477.10.21.20.3.34
		link20_1R4AlarmPower OBJECT-TYPE
			SYNTAX DisplayString
			MAX-ACCESS read-write
			STATUS current
			DESCRIPTION
				"get or set the power alarm threshold of 1R4 in link20."
			::= { link20OBP 34 }

--  1.3.6.1.4.1.47477.10.21.20.3.45
		-- 1.3.6.1.4.1.47477.10.21.20.3.45
		link20_2R1AlarmPower OBJECT-TYPE
			SYNTAX DisplayString
			MAX-ACCESS read-write
			STATUS current
			DESCRIPTION
				"get or set the power alarm threshold of 2R1 in link20."
			::= { link20OBP 45 }
			
--  1.3.6.1.4.1.47477.10.21.20.3.46
		-- 1.3.6.1.4.1.47477.10.21.20.3.46
		link20_2R2AlarmPower OBJECT-TYPE
			SYNTAX DisplayString
			MAX-ACCESS read-write
			STATUS current
			DESCRIPTION
				"get or set the power alarm threshold of 2R2 in link20."
			::= { link20OBP 46 }

--  1.3.6.1.4.1.47477.10.21.20.3.47
		-- 1.3.6.1.4.1.47477.10.21.20.3.47
		link20_2R3AlarmPower OBJECT-TYPE
			SYNTAX DisplayString
			MAX-ACCESS read-write
			STATUS current
			DESCRIPTION
				"get or set the power alarm threshold of 2R3 in link20."
			::= { link20OBP 47 }
			
--  1.3.6.1.4.1.47477.10.21.20.3.48
		-- 1.3.6.1.4.1.47477.10.21.20.3.48
		link20_2R4AlarmPower OBJECT-TYPE
			SYNTAX DisplayString
			MAX-ACCESS read-write
			STATUS current
			DESCRIPTION
				"get or set the power alarm threshold of 2R4 in link20."
			::= { link20OBP 48 }
			
--  1.3.6.1.4.1.47477.10.21.20.3.11
		-- 1.3.6.1.4.1.47477.10.21.20.3.11
		link20_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link20OBP 11 }
			
--  1.3.6.1.4.1.47477.10.21.20.3.67
		-- 1.3.6.1.4.1.47477.10.21.20.3.67
		link20_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link20OBP 67 }
			
--  1.3.6.1.4.1.47477.10.21.20.3.68
		-- 1.3.6.1.4.1.47477.10.21.20.3.68
		link20_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link20OBP 68 }
			
--  1.3.6.1.4.1.47477.10.21.20.3.12
		-- 1.3.6.1.4.1.47477.10.21.20.3.12
		link20_ReturnDelay OBJECT-TYPE
			--SYNTAX Integer32
			SYNTAX Integer32
			MAX-ACCESS read-write
			STATUS current
			DESCRIPTION
				"get or set how long link20 takes to return to automatic mode."
			::= { link20OBP 12 }
			
--  1.3.6.1.4.1.47477.10.21.20.3.13
		-- 1.3.6.1.4.1.47477.10.21.20.3.13
		link20_BackMode OBJECT-TYPE
			SYNTAX INTEGER
				{
				autoNoBack(0),
				autoBack(1)
				}
			MAX-ACCESS read-write
			STATUS current
			DESCRIPTION
				"get or set the back mode of link20."
			::= { link20OBP 13 }

		
--  1.3.6.1.4.1.47477.10.21.20.3.14
		-- 1.3.6.1.4.1.47477.10.21.20.3.14
		link20_BackDelay OBJECT-TYPE
			SYNTAX Integer32
			MAX-ACCESS read-write
			STATUS current
			DESCRIPTION
				"get or set the back delay."
			::= { link20OBP 14 }

--  1.3.6.1.4.1.47477.10.21.20.3.15
		-- 1.3.6.1.4.1.47477.10.21.20.3.15
		link20_ActiveHeartSwitch OBJECT-TYPE
			SYNTAX INTEGER
				{
				off(0),
				on(1)
				}
			MAX-ACCESS read-write
			STATUS current
			DESCRIPTION
				"get or set the switch status of active heartbeat."
			::= { link20OBP 15 }

		
--  1.3.6.1.4.1.47477.10.21.20.3.16
		-- 1.3.6.1.4.1.47477.10.21.20.3.16
		link20_ActiveSendInterval OBJECT-TYPE
			SYNTAX Integer32
			MAX-ACCESS read-write
			STATUS current
			DESCRIPTION
				"get or set the send interval of active heartbeat."
			::= { link20OBP 16 }		

--  1.3.6.1.4.1.47477.10.21.20.3.17
		-- 1.3.6.1.4.1.47477.10.21.20.3.17
		link20_ActiveTimeOut OBJECT-TYPE
			SYNTAX Integer32
			MAX-ACCESS read-write
			STATUS current
			DESCRIPTION
				"get or set how long the active heartbeat send timeout."
			::= { link20OBP 17 }

--  1.3.6.1.4.1.47477.10.21.20.3.18
		-- 1.3.6.1.4.1.47477.10.21.20.3.18
		link20_ActiveLossBypass OBJECT-TYPE
			SYNTAX Integer32
			MAX-ACCESS read-write
			STATUS current
			DESCRIPTION
				"get or set the bypass for active heartbeat packet loss."
			::= { link20OBP 18 }

--  1.3.6.1.4.1.47477.10.21.20.3.19
		-- 1.3.6.1.4.1.47477.10.21.20.3.19
		link20_PingIpAddress OBJECT-TYPE
			SYNTAX IpAddress
			MAX-ACCESS read-write
			STATUS current
			DESCRIPTION
				"get or set the ping ip address of link20."
			::= { link20OBP 19 }

--  1.3.6.1.4.1.47477.10.21.20.3.20
		-- 1.3.6.1.4.1.47477.10.21.20.3.20
		link20_PassiveHeartSwitch OBJECT-TYPE
			SYNTAX INTEGER
				{
				off(0),
				on(1)
				}
			MAX-ACCESS read-write
			STATUS current
			DESCRIPTION
				"get or set the switch status of passive heartbeat."
			::= { link20OBP 20 }
	

--  1.3.6.1.4.1.47477.10.21.20.3.21
		-- 1.3.6.1.4.1.47477.10.21.20.3.21
		link20_PassiveTimeOut OBJECT-TYPE
			SYNTAX Integer32
			MAX-ACCESS read-write
			STATUS current
			DESCRIPTION
				"get or set how long the passive heartbeat send timeout."
			::= { link20OBP 21 }

--  1.3.6.1.4.1.47477.10.21.20.3.22
		-- 1.3.6.1.4.1.47477.10.21.20.3.22
		link20_PassiveLossBypass OBJECT-TYPE
			SYNTAX Integer32
			MAX-ACCESS read-write
			STATUS current
			DESCRIPTION
				"get or set the bypass for passive heartbeat packet loss."
			::= { link20OBP 22 }

--  1.3.6.1.4.1.47477.10.21.20.3.23
		-- 1.3.6.1.4.1.47477.10.21.20.3.23
		link20_SwitchProtect OBJECT-TYPE
			SYNTAX INTEGER
				{
				off(0),
				on(1)
				}
			MAX-ACCESS read-write
			STATUS current
			DESCRIPTION
				"get or set the switch protection status of link20."
			::= { link20OBP 23 }
			
--  1.3.6.1.4.1.47477.10.21.20.3.24
		-- 1.3.6.1.4.1.47477.10.21.20.3.24
		link20_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link20OBP 24 }		

--  1.3.6.1.4.1.47477.10.21.20.3.25
		-- 1.3.6.1.4.1.47477.10.21.20.3.25
		link20_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link20OBP 25 }	

--  1.3.6.1.4.1.47477.10.21.20.3.26
		-- 1.3.6.1.4.1.47477.10.21.20.3.26
		link20_PowerAlarmStatus OBJECT-TYPE
			SYNTAX INTEGER
				{
				off(0),
				alarm(1),
				normal(2),
				na(3)
				}
			MAX-ACCESS read-only
			STATUS current
			DESCRIPTION
				"get whether a power alarm is generated."
			::= { link20OBP 26 }	


-- 1.3.6.1.4.1.47477.10.21.20.3.50.1
	link20_WorkModeChange 	OBJECT-TYPE    
    SYNTAX INTEGER	{
				manualMode(0),
				autoMode(1)
		}
	MAX-ACCESS read-only
	STATUS current
    DESCRIPTION
        "The Link mode Changed."
    ::= {link20OBPTrap 1}

-- 1.3.6.1.4.1.47477.10.21.20.3.50.2
	link20_StateChange 	OBJECT-TYPE    
    SYNTAX INTEGER	{
				bypass(0),
				primary(1)
		}
	MAX-ACCESS read-only
	STATUS current
    DESCRIPTION
        "The Link State(Channel) Changed."
    ::= {link20OBPTrap 2}

-- 1.3.6.1.4.1.47477.10.21.20.3.50.3
	link20_R1WaveSet 	OBJECT-TYPE    
    SYNTAX INTEGER	{
				w1310nm(0),
				w1550nm(1)
		}
	MAX-ACCESS read-only
	STATUS current
    DESCRIPTION
        "Set The link20 R1 Wave."
    ::= {link20OBPTrap 3}

-- 1.3.6.1.4.1.47477.10.21.20.3.50.4
	link20_R2WaveSet 	OBJECT-TYPE    
    SYNTAX INTEGER	{
				w1310nm(0),
				w1550nm(1)
		}
	MAX-ACCESS read-only
	STATUS current
    DESCRIPTION
        "Set The link20 R2 Wave."
    ::= {link20OBPTrap 4}			

-- 1.3.6.1.4.1.47477.10.21.20.3.50.5
	link20_R3WaveSet 	OBJECT-TYPE    
    SYNTAX INTEGER	{
				w1310nm(0),
				w1550nm(1)
		}
	MAX-ACCESS read-only
	STATUS current
    DESCRIPTION
        "Set The link20 R3 Wave."
    ::= {link20OBPTrap 5}

-- 1.3.6.1.4.1.47477.10.21.20.3.50.6
	link20_R4WaveSet 	OBJECT-TYPE    
    SYNTAX INTEGER	{
				w1310nm(0),
				w1550nm(1)
		}
	MAX-ACCESS read-only
	STATUS current
    DESCRIPTION
        "Set The link20 R4 Wave."
    ::= {link20OBPTrap 6}	
	
-- 1.3.6.1.4.1.47477.10.21.20.3.50.7
	link20_R1AlarmSet 	OBJECT-TYPE    
    SYNTAX DisplayString
	MAX-ACCESS read-only
	STATUS current
    DESCRIPTION
        "Set The link20 R1 Alarm Threshold."
    ::= {link20OBPTrap 7}

-- 1.3.6.1.4.1.47477.10.21.20.3.50.8
	link20_R2AlarmSet 	OBJECT-TYPE    
    SYNTAX DisplayString
	MAX-ACCESS read-only
	STATUS current
    DESCRIPTION
        "Set The link20 R2 Alarm Threshold."
    ::= {link20OBPTrap 8}
	
-- 1.3.6.1.4.1.47477.10.21.20.3.50.9
	link20_R3AlarmSet 	OBJECT-TYPE    
    SYNTAX DisplayString
	MAX-ACCESS read-only
	STATUS current
    DESCRIPTION
        "Set The link20 R3 Alarm Threshold."
    ::= {link20OBPTrap 9}

-- 1.3.6.1.4.1.47477.10.21.20.3.50.10
	link20_R4AlarmSet 	OBJECT-TYPE    
    SYNTAX DisplayString
	MAX-ACCESS read-only
	STATUS current
    DESCRIPTION
        "Set The link20 R4 Alarm Threshold."
    ::= {link20OBPTrap 10}	
	
	
-- 1.3.6.1.4.1.47477.10.21.20.3.50.11
	link20_1R1AlarmSet 	OBJECT-TYPE    
    SYNTAX DisplayString
	MAX-ACCESS read-only
	STATUS current
    DESCRIPTION
        "Set The link20 1R1 Alarm Threshold."
    ::= {link20OBPTrap 11}

-- 1.3.6.1.4.1.47477.10.21.20.3.50.12
	link20_2R1AlarmSet 	OBJECT-TYPE    
    SYNTAX DisplayString
	MAX-ACCESS read-only
	STATUS current
    DESCRIPTION
        "Set The link20 2R1 Alarm Threshold."
    ::= {link20OBPTrap 12}
	
-- 1.3.6.1.4.1.47477.10.21.20.3.50.13
	link20_1R2AlarmSet 	OBJECT-TYPE    
    SYNTAX DisplayString
	MAX-ACCESS read-only
	STATUS current
    DESCRIPTION
        "Set The link20 1R2 Alarm Threshold."
    ::= {link20OBPTrap 13}

-- 1.3.6.1.4.1.47477.10.21.20.3.50.14
	link20_2R2AlarmSet 	OBJECT-TYPE    
    SYNTAX DisplayString
	MAX-ACCESS read-only
	STATUS current
    DESCRIPTION
        "Set The link20 2R2 Alarm Threshold."
    ::= {link20OBPTrap 14}
	
-- 1.3.6.1.4.1.47477.10.21.20.3.50.15
	link20_1R3AlarmSet 	OBJECT-TYPE    
    SYNTAX DisplayString
	MAX-ACCESS read-only
	STATUS current
    DESCRIPTION
        "Set The link20 1R3 Alarm Threshold."
    ::= {link20OBPTrap 15}

-- 1.3.6.1.4.1.47477.10.21.20.3.50.16
	link20_2R3AlarmSet 	OBJECT-TYPE    
    SYNTAX DisplayString
	MAX-ACCESS read-only
	STATUS current
    DESCRIPTION
        "Set The link20 2R3 Alarm Threshold."
    ::= {link20OBPTrap 16}
	
-- 1.3.6.1.4.1.47477.10.21.20.3.50.17
	link20_1R4AlarmSet 	OBJECT-TYPE    
    SYNTAX DisplayString
	MAX-ACCESS read-only
	STATUS current
    DESCRIPTION
        "Set The link20 1R4 Alarm Threshold."
    ::= {link20OBPTrap 17}

-- 1.3.6.1.4.1.47477.10.21.20.3.50.18
	link20_2R4AlarmSet 	OBJECT-TYPE    
    SYNTAX DisplayString
	MAX-ACCESS read-only
	STATUS current
    DESCRIPTION
        "Set The link20 2R4 Alarm Threshold."
    ::= {link20OBPTrap 18}
	
-- 1.3.6.1.4.1.47477.10.21.20.3.50.19
	link20_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link20 PowerAlarmBypass2 Changed."
    ::= {link20OBPTrap 19}
	
-- 1.3.6.1.4.1.47477.10.21.20.3.50.20
	link20_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link20 PowerAlarmBypass4 Changed."
    ::= {link20OBPTrap 20}	
	
-- 1.3.6.1.4.1.47477.10.21.20.3.50.21
	link20_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link20 PowerAlarmBypass8 Changed."
    ::= {link20OBPTrap 21}
	
-- 1.3.6.1.4.1.47477.10.21.20.3.50.22
	link20_powerAlarmR1 	OBJECT-TYPE    
    SYNTAX DisplayString
	MAX-ACCESS read-only
	STATUS current
    DESCRIPTION
        "Set The link20 R1 Power Status Alarm."
    ::= {link20OBPTrap 22}
	
-- 1.3.6.1.4.1.47477.10.21.20.3.50.23
	link20_powerAlarmR2 	OBJECT-TYPE    
    SYNTAX DisplayString
	MAX-ACCESS read-only
	STATUS current
    DESCRIPTION
        "Set The link20 R2 Power Status Alarm."
    ::= {link20OBPTrap 23}
	
-- 1.3.6.1.4.1.47477.10.21.20.3.50.24
	link20_powerAlarmR3 	OBJECT-TYPE    
    SYNTAX DisplayString
	MAX-ACCESS read-only
	STATUS current
    DESCRIPTION
        "Set The link20 R3 Power Status Alarm."
    ::= {link20OBPTrap 24}
	
-- 1.3.6.1.4.1.47477.10.21.20.3.50.25
	link20_powerAlarmR4 	OBJECT-TYPE    
    SYNTAX DisplayString
	MAX-ACCESS read-only
	STATUS current
    DESCRIPTION
        "Set The link20 R4 Power Status Alarm."
    ::= {link20OBPTrap 25}
	
	
-- 1.3.6.1.4.1.47477.10.21.20.3.50.26
	link20_powerAlarm1R1 	OBJECT-TYPE    
    SYNTAX DisplayString
	MAX-ACCESS read-only
	STATUS current
    DESCRIPTION
        "Set The link20 1R1 Power Status Alarm."
    ::= {link20OBPTrap 26}
	
-- 1.3.6.1.4.1.47477.10.21.20.3.50.27
	link20_powerAlarm2R1 	OBJECT-TYPE    
    SYNTAX DisplayString
	MAX-ACCESS read-only
	STATUS current
    DESCRIPTION
        "Set The link20 2R1 Power Status Alarm."
    ::= {link20OBPTrap 27}
	
-- 1.3.6.1.4.1.47477.10.21.20.3.50.28
	link20_powerAlarm1R2 	OBJECT-TYPE    
    SYNTAX DisplayString
	MAX-ACCESS read-only
	STATUS current
    DESCRIPTION
        "Set The link20 1R2 Power Status Alarm."
    ::= {link20OBPTrap 28}
	
-- 1.3.6.1.4.1.47477.10.21.20.3.50.29
	link20_powerAlarm2R2 	OBJECT-TYPE    
    SYNTAX DisplayString
	MAX-ACCESS read-only
	STATUS current
    DESCRIPTION
        "Set The link20 2R2 Power Status Alarm."
    ::= {link20OBPTrap 29}
	
-- 1.3.6.1.4.1.47477.10.21.20.3.50.30
	link20_powerAlarm1R3 	OBJECT-TYPE    
    SYNTAX DisplayString
	MAX-ACCESS read-only
	STATUS current
    DESCRIPTION
        "Set The link20 1R3 Power Status Alarm."
    ::= {link20OBPTrap 30}
	
-- 1.3.6.1.4.1.47477.10.21.20.3.50.31
	link20_powerAlarm2R3 	OBJECT-TYPE    
    SYNTAX DisplayString
	MAX-ACCESS read-only
	STATUS current
    DESCRIPTION
        "Set The link20 2R1 Power Status Alarm."
    ::= {link20OBPTrap 31}
	
-- 1.3.6.1.4.1.47477.10.21.20.3.50.32
	link20_powerAlarm1R4 	OBJECT-TYPE    
    SYNTAX DisplayString
	MAX-ACCESS read-only
	STATUS current
    DESCRIPTION
        "Set The link20 1R4 Power Status Alarm."
    ::= {link20OBPTrap 32}
	
-- 1.3.6.1.4.1.47477.10.21.20.3.50.33
	link20_powerAlarm2R4 	OBJECT-TYPE    
    SYNTAX DisplayString
	MAX-ACCESS read-only
	STATUS current
    DESCRIPTION
        "Set The link20 2R4 Power Status Alarm."
    ::= {link20OBPTrap 33}
	
--  1.3.6.1.4.1.47477.10.21.21.3.1
		-- 1.3.6.1.4.1.47477.10.21.21.3.1
		link21_State OBJECT-TYPE
			SYNTAX INTEGER
				{
				off(0),
				on(1)
				}
			MAX-ACCESS read-only
			STATUS current
			DESCRIPTION
				"get the information about whether link21 is working."
			::= { link21OBP 1 }

		
--  1.3.6.1.4.1.47477.10.21.21.3.2
		-- 1.3.6.1.4.1.47477.10.21.21.3.2
		link21_DeviceType OBJECT-TYPE
			SYNTAX DisplayString
			MAX-ACCESS read-only
			STATUS current
			DESCRIPTION
				"get the type of card in link21."
			::= { link21OBP 2 }

			
--  1.3.6.1.4.1.47477.10.21.21.3.3
		-- 1.3.6.1.4.1.47477.10.21.21.3.3
		link21_WorkMode OBJECT-TYPE
			SYNTAX INTEGER
				{
				manualMode(0),
				autoMode(1)
				}
			MAX-ACCESS read-write
			STATUS current
			DESCRIPTION
				"get or set link21's work mode."
			::= { link21OBP 3 }

		
--  1.3.6.1.4.1.47477.10.21.21.3.4
		-- 1.3.6.1.4.1.47477.10.21.21.3.4
		link21_Channel OBJECT-TYPE
			SYNTAX INTEGER
				{
				bypass(0),
				primary(1)
				}
			MAX-ACCESS read-write
			STATUS current
			DESCRIPTION
				"get or set the channel in which link21 works."
			::= { link21OBP 4 }


--  1.3.6.1.4.1.47477.10.21.21.3.5
		-- 1.3.6.1.4.1.47477.10.21.21.3.5
		link21_R1Power OBJECT-TYPE
			SYNTAX DisplayString
			MAX-ACCESS read-only
			STATUS current
			DESCRIPTION
				"get the power of R1 in link21."
			::= { link21OBP 5 }

		
--  1.3.6.1.4.1.47477.10.21.21.3.6
		-- 1.3.6.1.4.1.47477.10.21.21.3.6
		link21_R2Power OBJECT-TYPE
			SYNTAX DisplayString
			MAX-ACCESS read-only
			STATUS current
			DESCRIPTION
				"get the power of R2 in link21."
			::= { link21OBP 6 }
			
--  1.3.6.1.4.1.47477.10.21.21.3.35
		-- 1.3.6.1.4.1.47477.10.21.21.3.35
		link21_R3Power OBJECT-TYPE
			SYNTAX DisplayString
			MAX-ACCESS read-only
			STATUS current
			DESCRIPTION
				"get the power of R3 in link21."
			::= { link21OBP 35 }
			
--  1.3.6.1.4.1.47477.10.21.21.3.36
		-- 1.3.6.1.4.1.47477.10.21.21.3.36
		link21_R4Power OBJECT-TYPE
			SYNTAX DisplayString
			MAX-ACCESS read-only
			STATUS current
			DESCRIPTION
				"get the power of R4 in link21."
			::= { link21OBP 36 }		
		
--  1.3.6.1.4.1.47477.10.21.21.3.7
		-- 1.3.6.1.4.1.47477.10.21.21.3.7
		link21_R1Wave OBJECT-TYPE
			SYNTAX INTEGER
				{
				w1310nm(0),
				w1550nm(1),
				na(2)
				}
			MAX-ACCESS read-write
			STATUS current
			DESCRIPTION
				"get or set the wave length of R1 in link21."
			::= { link21OBP 7 }

		
--  1.3.6.1.4.1.47477.10.21.21.3.8
		-- 1.3.6.1.4.1.47477.10.21.21.3.8
		link21_R2Wave OBJECT-TYPE
			SYNTAX INTEGER
				{
				w1310nm(0),
				w1550nm(1),
				na(2)
				}
			MAX-ACCESS read-write
			STATUS current
			DESCRIPTION
				"get or set the wave length of R2 in link21."
			::= { link21OBP 8 }


--  1.3.6.1.4.1.47477.10.21.21.3.27
		-- 1.3.6.1.4.1.47477.10.21.21.3.27
		link21_R3Wave OBJECT-TYPE
			SYNTAX INTEGER
				{
				w1310nm(0),
				w1550nm(1),
				na(2)
				}
			MAX-ACCESS read-write
			STATUS current
			DESCRIPTION
				"get or set the wave length of R3 in link21."
			::= { link21OBP 27 }

		
--  1.3.6.1.4.1.47477.10.21.21.3.28
		-- 1.3.6.1.4.1.47477.10.21.21.3.28
		link21_R4Wave OBJECT-TYPE
			SYNTAX INTEGER
				{
				w1310nm(0),
				w1550nm(1),
				na(2)
				}
			MAX-ACCESS read-write
			STATUS current
			DESCRIPTION
				"get or set the wave length of R4 in link21."
			::= { link21OBP 28 }
			
--  1.3.6.1.4.1.47477.10.21.21.3.9
		-- 1.3.6.1.4.1.47477.10.21.21.3.9
		link21_R1AlarmPower OBJECT-TYPE
			SYNTAX DisplayString
			MAX-ACCESS read-write
			STATUS current
			DESCRIPTION
				"get or set the power alarm threshold of R1 in link21."
			::= { link21OBP 9 }

		
--  1.3.6.1.4.1.47477.10.21.21.3.10
		-- 1.3.6.1.4.1.47477.10.21.21.3.10
		link21_R2AlarmPower OBJECT-TYPE
			SYNTAX DisplayString
			MAX-ACCESS read-write
			STATUS current
			DESCRIPTION
				"get or set the power alarm threshold of R2 in link21."
			::= { link21OBP 10 }


--  1.3.6.1.4.1.47477.10.21.21.3.29
		-- 1.3.6.1.4.1.47477.10.21.21.3.29
		link21_R3AlarmPower OBJECT-TYPE
			SYNTAX DisplayString
			MAX-ACCESS read-write
			STATUS current
			DESCRIPTION
				"get or set the power alarm threshold of R3 in link21."
			::= { link21OBP 29 }

		
--  1.3.6.1.4.1.47477.10.21.21.3.30
		-- 1.3.6.1.4.1.47477.10.21.21.3.30
		link21_R4AlarmPower OBJECT-TYPE
			SYNTAX DisplayString
			MAX-ACCESS read-write
			STATUS current
			DESCRIPTION
				"get or set the power alarm threshold of R4 in link21."
			::= { link21OBP 30 }

-- OBP4
--  1.3.6.1.4.1.47477.10.21.21.3.37
		-- 1.3.6.1.4.1.47477.10.21.21.3.37
		link21_1R1Power OBJECT-TYPE
			SYNTAX DisplayString
			MAX-ACCESS read-only
			STATUS current
			DESCRIPTION
				"get the power of 1R1 in link21."
			::= { link21OBP 37 }
			
--  1.3.6.1.4.1.47477.10.21.21.3.38
		-- 1.3.6.1.4.1.47477.10.21.21.3.38
		link21_1R2Power OBJECT-TYPE
			SYNTAX DisplayString
			MAX-ACCESS read-only
			STATUS current
			DESCRIPTION
				"get the power of 1R2 in link21."
			::= { link21OBP 38 }

--  1.3.6.1.4.1.47477.10.21.21.3.39
		-- 1.3.6.1.4.1.47477.10.21.21.3.39
		link21_1R3Power OBJECT-TYPE
			SYNTAX DisplayString
			MAX-ACCESS read-only
			STATUS current
			DESCRIPTION
				"get the power of 1R3 in link21."
			::= { link21OBP 39 }
			
--  1.3.6.1.4.1.47477.10.21.21.3.40
		-- 1.3.6.1.4.1.47477.10.21.21.3.40
		link21_1R4Power OBJECT-TYPE
			SYNTAX DisplayString
			MAX-ACCESS read-only
			STATUS current
			DESCRIPTION
				"get the power of 1R4 in link21."
			::= { link21OBP 40 }

--  1.3.6.1.4.1.47477.10.21.21.3.41
		-- 1.3.6.1.4.1.47477.10.21.21.3.41
		link21_2R1Power OBJECT-TYPE
			SYNTAX DisplayString
			MAX-ACCESS read-only
			STATUS current
			DESCRIPTION
				"get the power of 2R1 in link21."
			::= { link21OBP 41 }
			
--  1.3.6.1.4.1.47477.10.21.21.3.42
		-- 1.3.6.1.4.1.47477.10.21.21.3.42
		link21_2R2Power OBJECT-TYPE
			SYNTAX DisplayString
			MAX-ACCESS read-only
			STATUS current
			DESCRIPTION
				"get the power of 2R2 in link21."
			::= { link21OBP 42 }

--  1.3.6.1.4.1.47477.10.21.21.3.41
		-- 1.3.6.1.4.1.47477.10.21.21.3.43
		link21_2R3Power OBJECT-TYPE
			SYNTAX DisplayString
			MAX-ACCESS read-only
			STATUS current
			DESCRIPTION
				"get the power of 2R3 in link21."
			::= { link21OBP 43 }
			
--  1.3.6.1.4.1.47477.10.21.21.3.42
		-- 1.3.6.1.4.1.47477.10.21.21.3.44
		link21_2R4Power OBJECT-TYPE
			SYNTAX DisplayString
			MAX-ACCESS read-only
			STATUS current
			DESCRIPTION
				"get the power of 2R4 in link21."
			::= { link21OBP 44 }
			
--  1.3.6.1.4.1.47477.10.21.21.3.49
		-- 1.3.6.1.4.1.47477.10.21.21.3.49
		link21_1R1Wave OBJECT-TYPE
			SYNTAX INTEGER
				{
				w850nm(0),
				na(2)
				}
			MAX-ACCESS read-only
			STATUS current
			DESCRIPTION
				"get the wave length of 1R1 in link21."
			::= { link21OBP 49 }
		
--  1.3.6.1.4.1.47477.10.21.21.3.60
		-- 1.3.6.1.4.1.47477.10.21.21.3.60
		link21_1R2Wave OBJECT-TYPE
			SYNTAX INTEGER
				{
				w850nm(0),
				na(2)
				}
			MAX-ACCESS read-only
			STATUS current
			DESCRIPTION
				"get the wave length of 1R2 in link21."
			::= { link21OBP 60 }

--  1.3.6.1.4.1.47477.10.21.21.3.61
		-- 1.3.6.1.4.1.47477.10.21.21.3.61
		link21_1R3Wave OBJECT-TYPE
			SYNTAX INTEGER
				{
				w850nm(0),
				na(2)
				}
			MAX-ACCESS read-only
			STATUS current
			DESCRIPTION
				"get the wave length of 1R3 in link21."
			::= { link21OBP 61 }

		
--  1.3.6.1.4.1.47477.10.21.21.3.62
		-- 1.3.6.1.4.1.47477.10.21.21.3.62
		link21_1R4Wave OBJECT-TYPE
			SYNTAX INTEGER
				{
				w850nm(0),
				na(2)
				}
			MAX-ACCESS read-only
			STATUS current
			DESCRIPTION
				"get the wave length of 1R4 in link21."
			::= { link21OBP 62 }
	
--  1.3.6.1.4.1.47477.10.21.21.3.63
		-- 1.3.6.1.4.1.47477.10.21.21.3.63
		link21_2R1Wave OBJECT-TYPE
			SYNTAX INTEGER
				{
				w850nm(0),
				na(2)
				}
			MAX-ACCESS read-only
			STATUS current
			DESCRIPTION
				"get the wave length of 2R1 in link21."
			::= { link21OBP 63 }

		
--  1.3.6.1.4.1.47477.10.21.21.3.64
		-- 1.3.6.1.4.1.47477.10.21.21.3.64
		link21_2R2Wave OBJECT-TYPE
			SYNTAX INTEGER
				{
				w850nm(0),
				na(2)
				}
			MAX-ACCESS read-only
			STATUS current
			DESCRIPTION
				"get the wave length of 2R2 in link21."
			::= { link21OBP 64 }	
	
--  1.3.6.1.4.1.47477.10.21.21.3.65
		-- 1.3.6.1.4.1.47477.10.21.21.3.65
		link21_2R3Wave OBJECT-TYPE
			SYNTAX INTEGER
				{
				w850nm(0),
				na(2)
				}
			MAX-ACCESS read-only
			STATUS current
			DESCRIPTION
				"get the wave length of 2R3 in link21."
			::= { link21OBP 65 }

		
--  1.3.6.1.4.1.47477.10.21.21.3.66
		-- 1.3.6.1.4.1.47477.10.21.21.3.66
		link21_2R4Wave OBJECT-TYPE
			SYNTAX INTEGER
				{
				w850nm(0),
				na(2)
				}
			MAX-ACCESS read-only
			STATUS current
			DESCRIPTION
				"get the wave length of 2R4 in link21."
			::= { link21OBP 66 }	
			
--  1.3.6.1.4.1.47477.10.21.21.3.31
		-- 1.3.6.1.4.1.47477.10.21.21.3.31
		link21_1R1AlarmPower OBJECT-TYPE
			SYNTAX DisplayString
			MAX-ACCESS read-write
			STATUS current
			DESCRIPTION
				"get or set the power alarm threshold of 1R1 in link21."
			::= { link21OBP 31 }
			
--  1.3.6.1.4.1.47477.10.21.21.3.32
		-- 1.3.6.1.4.1.47477.10.21.21.3.32
		link21_1R2AlarmPower OBJECT-TYPE
			SYNTAX DisplayString
			MAX-ACCESS read-write
			STATUS current
			DESCRIPTION
				"get or set the power alarm threshold of 1R2 in link21."
			::= { link21OBP 32 }

--  1.3.6.1.4.1.47477.10.21.21.3.33
		-- 1.3.6.1.4.1.47477.10.21.21.3.33
		link21_1R3AlarmPower OBJECT-TYPE
			SYNTAX DisplayString
			MAX-ACCESS read-write
			STATUS current
			DESCRIPTION
				"get or set the power alarm threshold of 1R3 in link21."
			::= { link21OBP 33 }
			
--  1.3.6.1.4.1.47477.10.21.21.3.34
		-- 1.3.6.1.4.1.47477.10.21.21.3.34
		link21_1R4AlarmPower OBJECT-TYPE
			SYNTAX DisplayString
			MAX-ACCESS read-write
			STATUS current
			DESCRIPTION
				"get or set the power alarm threshold of 1R4 in link21."
			::= { link21OBP 34 }

--  1.3.6.1.4.1.47477.10.21.21.3.45
		-- 1.3.6.1.4.1.47477.10.21.21.3.45
		link21_2R1AlarmPower OBJECT-TYPE
			SYNTAX DisplayString
			MAX-ACCESS read-write
			STATUS current
			DESCRIPTION
				"get or set the power alarm threshold of 2R1 in link21."
			::= { link21OBP 45 }
			
--  1.3.6.1.4.1.47477.10.21.21.3.46
		-- 1.3.6.1.4.1.47477.10.21.21.3.46
		link21_2R2AlarmPower OBJECT-TYPE
			SYNTAX DisplayString
			MAX-ACCESS read-write
			STATUS current
			DESCRIPTION
				"get or set the power alarm threshold of 2R2 in link21."
			::= { link21OBP 46 }

--  1.3.6.1.4.1.47477.10.21.21.3.47
		-- 1.3.6.1.4.1.47477.10.21.21.3.47
		link21_2R3AlarmPower OBJECT-TYPE
			SYNTAX DisplayString
			MAX-ACCESS read-write
			STATUS current
			DESCRIPTION
				"get or set the power alarm threshold of 2R3 in link21."
			::= { link21OBP 47 }
			
--  1.3.6.1.4.1.47477.10.21.21.3.48
		-- 1.3.6.1.4.1.47477.10.21.21.3.48
		link21_2R4AlarmPower OBJECT-TYPE
			SYNTAX DisplayString
			MAX-ACCESS read-write
			STATUS current
			DESCRIPTION
				"get or set the power alarm threshold of 2R4 in link21."
			::= { link21OBP 48 }
			
--  1.3.6.1.4.1.47477.10.21.21.3.11
		-- 1.3.6.1.4.1.47477.10.21.21.3.11
		link21_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link21OBP 11 }
			
--  1.3.6.1.4.1.47477.10.21.21.3.67
		-- 1.3.6.1.4.1.47477.10.21.21.3.67
		link21_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link21OBP 67 }
			
--  1.3.6.1.4.1.47477.10.21.21.3.68
		-- 1.3.6.1.4.1.47477.10.21.21.3.68
		link21_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link21OBP 68 }
			
--  1.3.6.1.4.1.47477.10.21.21.3.12
		-- 1.3.6.1.4.1.47477.10.21.21.3.12
		link21_ReturnDelay OBJECT-TYPE
			--SYNTAX Integer32
			SYNTAX Integer32
			MAX-ACCESS read-write
			STATUS current
			DESCRIPTION
				"get or set how long link21 takes to return to automatic mode."
			::= { link21OBP 12 }
			
--  1.3.6.1.4.1.47477.10.21.21.3.13
		-- 1.3.6.1.4.1.47477.10.21.21.3.13
		link21_BackMode OBJECT-TYPE
			SYNTAX INTEGER
				{
				autoNoBack(0),
				autoBack(1)
				}
			MAX-ACCESS read-write
			STATUS current
			DESCRIPTION
				"get or set the back mode of link21."
			::= { link21OBP 13 }

		
--  1.3.6.1.4.1.47477.10.21.21.3.14
		-- 1.3.6.1.4.1.47477.10.21.21.3.14
		link21_BackDelay OBJECT-TYPE
			SYNTAX Integer32
			MAX-ACCESS read-write
			STATUS current
			DESCRIPTION
				"get or set the back delay."
			::= { link21OBP 14 }

--  1.3.6.1.4.1.47477.10.21.21.3.15
		-- 1.3.6.1.4.1.47477.10.21.21.3.15
		link21_ActiveHeartSwitch OBJECT-TYPE
			SYNTAX INTEGER
				{
				off(0),
				on(1)
				}
			MAX-ACCESS read-write
			STATUS current
			DESCRIPTION
				"get or set the switch status of active heartbeat."
			::= { link21OBP 15 }

		
--  1.3.6.1.4.1.47477.10.21.21.3.16
		-- 1.3.6.1.4.1.47477.10.21.21.3.16
		link21_ActiveSendInterval OBJECT-TYPE
			SYNTAX Integer32
			MAX-ACCESS read-write
			STATUS current
			DESCRIPTION
				"get or set the send interval of active heartbeat."
			::= { link21OBP 16 }		

--  1.3.6.1.4.1.47477.10.21.21.3.17
		-- 1.3.6.1.4.1.47477.10.21.21.3.17
		link21_ActiveTimeOut OBJECT-TYPE
			SYNTAX Integer32
			MAX-ACCESS read-write
			STATUS current
			DESCRIPTION
				"get or set how long the active heartbeat send timeout."
			::= { link21OBP 17 }

--  1.3.6.1.4.1.47477.10.21.21.3.18
		-- 1.3.6.1.4.1.47477.10.21.21.3.18
		link21_ActiveLossBypass OBJECT-TYPE
			SYNTAX Integer32
			MAX-ACCESS read-write
			STATUS current
			DESCRIPTION
				"get or set the bypass for active heartbeat packet loss."
			::= { link21OBP 18 }

--  1.3.6.1.4.1.47477.10.21.21.3.19
		-- 1.3.6.1.4.1.47477.10.21.21.3.19
		link21_PingIpAddress OBJECT-TYPE
			SYNTAX IpAddress
			MAX-ACCESS read-write
			STATUS current
			DESCRIPTION
				"get or set the ping ip address of link21."
			::= { link21OBP 19 }

--  1.3.6.1.4.1.47477.10.21.21.3.20
		-- 1.3.6.1.4.1.47477.10.21.21.3.20
		link21_PassiveHeartSwitch OBJECT-TYPE
			SYNTAX INTEGER
				{
				off(0),
				on(1)
				}
			MAX-ACCESS read-write
			STATUS current
			DESCRIPTION
				"get or set the switch status of passive heartbeat."
			::= { link21OBP 20 }
	

--  1.3.6.1.4.1.47477.10.21.21.3.21
		-- 1.3.6.1.4.1.47477.10.21.21.3.21
		link21_PassiveTimeOut OBJECT-TYPE
			SYNTAX Integer32
			MAX-ACCESS read-write
			STATUS current
			DESCRIPTION
				"get or set how long the passive heartbeat send timeout."
			::= { link21OBP 21 }

--  1.3.6.1.4.1.47477.10.21.21.3.22
		-- 1.3.6.1.4.1.47477.10.21.21.3.22
		link21_PassiveLossBypass OBJECT-TYPE
			SYNTAX Integer32
			MAX-ACCESS read-write
			STATUS current
			DESCRIPTION
				"get or set the bypass for passive heartbeat packet loss."
			::= { link21OBP 22 }

--  1.3.6.1.4.1.47477.10.21.21.3.23
		-- 1.3.6.1.4.1.47477.10.21.21.3.23
		link21_SwitchProtect OBJECT-TYPE
			SYNTAX INTEGER
				{
				off(0),
				on(1)
				}
			MAX-ACCESS read-write
			STATUS current
			DESCRIPTION
				"get or set the switch protection status of link21."
			::= { link21OBP 23 }
			
--  1.3.6.1.4.1.47477.10.21.21.3.24
		-- 1.3.6.1.4.1.47477.10.21.21.3.24
		link21_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link21OBP 24 }		

--  1.3.6.1.4.1.47477.10.21.21.3.25
		-- 1.3.6.1.4.1.47477.10.21.21.3.25
		link21_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link21OBP 25 }	

--  1.3.6.1.4.1.47477.10.21.21.3.26
		-- 1.3.6.1.4.1.47477.10.21.21.3.26
		link21_PowerAlarmStatus OBJECT-TYPE
			SYNTAX INTEGER
				{
				off(0),
				alarm(1),
				normal(2),
				na(3)
				}
			MAX-ACCESS read-only
			STATUS current
			DESCRIPTION
				"get whether a power alarm is generated."
			::= { link21OBP 26 }	


-- 1.3.6.1.4.1.47477.10.21.21.3.50.1
	link21_WorkModeChange 	OBJECT-TYPE    
    SYNTAX INTEGER	{
				manualMode(0),
				autoMode(1)
		}
	MAX-ACCESS read-only
	STATUS current
    DESCRIPTION
        "The Link mode Changed."
    ::= {link21OBPTrap 1}

-- 1.3.6.1.4.1.47477.10.21.21.3.50.2
	link21_StateChange 	OBJECT-TYPE    
    SYNTAX INTEGER	{
				bypass(0),
				primary(1)
		}
	MAX-ACCESS read-only
	STATUS current
    DESCRIPTION
        "The Link State(Channel) Changed."
    ::= {link21OBPTrap 2}

-- 1.3.6.1.4.1.47477.10.21.21.3.50.3
	link21_R1WaveSet 	OBJECT-TYPE    
    SYNTAX INTEGER	{
				w1310nm(0),
				w1550nm(1)
		}
	MAX-ACCESS read-only
	STATUS current
    DESCRIPTION
        "Set The link21 R1 Wave."
    ::= {link21OBPTrap 3}

-- 1.3.6.1.4.1.47477.10.21.21.3.50.4
	link21_R2WaveSet 	OBJECT-TYPE    
    SYNTAX INTEGER	{
				w1310nm(0),
				w1550nm(1)
		}
	MAX-ACCESS read-only
	STATUS current
    DESCRIPTION
        "Set The link21 R2 Wave."
    ::= {link21OBPTrap 4}			

-- 1.3.6.1.4.1.47477.10.21.21.3.50.5
	link21_R3WaveSet 	OBJECT-TYPE    
    SYNTAX INTEGER	{
				w1310nm(0),
				w1550nm(1)
		}
	MAX-ACCESS read-only
	STATUS current
    DESCRIPTION
        "Set The link21 R3 Wave."
    ::= {link21OBPTrap 5}

-- 1.3.6.1.4.1.47477.10.21.21.3.50.6
	link21_R4WaveSet 	OBJECT-TYPE    
    SYNTAX INTEGER	{
				w1310nm(0),
				w1550nm(1)
		}
	MAX-ACCESS read-only
	STATUS current
    DESCRIPTION
        "Set The link21 R4 Wave."
    ::= {link21OBPTrap 6}	
	
-- 1.3.6.1.4.1.47477.10.21.21.3.50.7
	link21_R1AlarmSet 	OBJECT-TYPE    
    SYNTAX DisplayString
	MAX-ACCESS read-only
	STATUS current
    DESCRIPTION
        "Set The link21 R1 Alarm Threshold."
    ::= {link21OBPTrap 7}

-- 1.3.6.1.4.1.47477.10.21.21.3.50.8
	link21_R2AlarmSet 	OBJECT-TYPE    
    SYNTAX DisplayString
	MAX-ACCESS read-only
	STATUS current
    DESCRIPTION
        "Set The link21 R2 Alarm Threshold."
    ::= {link21OBPTrap 8}
	
-- 1.3.6.1.4.1.47477.10.21.21.3.50.9
	link21_R3AlarmSet 	OBJECT-TYPE    
    SYNTAX DisplayString
	MAX-ACCESS read-only
	STATUS current
    DESCRIPTION
        "Set The link21 R3 Alarm Threshold."
    ::= {link21OBPTrap 9}

-- 1.3.6.1.4.1.47477.10.21.21.3.50.10
	link21_R4AlarmSet 	OBJECT-TYPE    
    SYNTAX DisplayString
	MAX-ACCESS read-only
	STATUS current
    DESCRIPTION
        "Set The link21 R4 Alarm Threshold."
    ::= {link21OBPTrap 10}	
	
	
-- 1.3.6.1.4.1.47477.10.21.21.3.50.11
	link21_1R1AlarmSet 	OBJECT-TYPE    
    SYNTAX DisplayString
	MAX-ACCESS read-only
	STATUS current
    DESCRIPTION
        "Set The link21 1R1 Alarm Threshold."
    ::= {link21OBPTrap 11}

-- 1.3.6.1.4.1.47477.10.21.21.3.50.12
	link21_2R1AlarmSet 	OBJECT-TYPE    
    SYNTAX DisplayString
	MAX-ACCESS read-only
	STATUS current
    DESCRIPTION
        "Set The link21 2R1 Alarm Threshold."
    ::= {link21OBPTrap 12}
	
-- 1.3.6.1.4.1.47477.10.21.21.3.50.13
	link21_1R2AlarmSet 	OBJECT-TYPE    
    SYNTAX DisplayString
	MAX-ACCESS read-only
	STATUS current
    DESCRIPTION
        "Set The link21 1R2 Alarm Threshold."
    ::= {link21OBPTrap 13}

-- 1.3.6.1.4.1.47477.10.21.21.3.50.14
	link21_2R2AlarmSet 	OBJECT-TYPE    
    SYNTAX DisplayString
	MAX-ACCESS read-only
	STATUS current
    DESCRIPTION
        "Set The link21 2R2 Alarm Threshold."
    ::= {link21OBPTrap 14}
	
-- 1.3.6.1.4.1.47477.10.21.21.3.50.15
	link21_1R3AlarmSet 	OBJECT-TYPE    
    SYNTAX DisplayString
	MAX-ACCESS read-only
	STATUS current
    DESCRIPTION
        "Set The link21 1R3 Alarm Threshold."
    ::= {link21OBPTrap 15}

-- 1.3.6.1.4.1.47477.10.21.21.3.50.16
	link21_2R3AlarmSet 	OBJECT-TYPE    
    SYNTAX DisplayString
	MAX-ACCESS read-only
	STATUS current
    DESCRIPTION
        "Set The link21 2R3 Alarm Threshold."
    ::= {link21OBPTrap 16}
	
-- 1.3.6.1.4.1.47477.10.21.21.3.50.17
	link21_1R4AlarmSet 	OBJECT-TYPE    
    SYNTAX DisplayString
	MAX-ACCESS read-only
	STATUS current
    DESCRIPTION
        "Set The link21 1R4 Alarm Threshold."
    ::= {link21OBPTrap 17}

-- 1.3.6.1.4.1.47477.10.21.21.3.50.18
	link21_2R4AlarmSet 	OBJECT-TYPE    
    SYNTAX DisplayString
	MAX-ACCESS read-only
	STATUS current
    DESCRIPTION
        "Set The link21 2R4 Alarm Threshold."
    ::= {link21OBPTrap 18}
	
-- 1.3.6.1.4.1.47477.10.21.21.3.50.19
	link21_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link21 PowerAlarmBypass2 Changed."
    ::= {link21OBPTrap 19}
	
-- 1.3.6.1.4.1.47477.10.21.21.3.50.20
	link21_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link21 PowerAlarmBypass4 Changed."
    ::= {link21OBPTrap 20}	
	
-- 1.3.6.1.4.1.47477.10.21.21.3.50.21
	link21_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link21 PowerAlarmBypass8 Changed."
    ::= {link21OBPTrap 21}
	
-- 1.3.6.1.4.1.47477.10.21.21.3.50.22
	link21_powerAlarmR1 	OBJECT-TYPE    
    SYNTAX DisplayString
	MAX-ACCESS read-only
	STATUS current
    DESCRIPTION
        "Set The link21 R1 Power Status Alarm."
    ::= {link21OBPTrap 22}
	
-- 1.3.6.1.4.1.47477.10.21.21.3.50.23
	link21_powerAlarmR2 	OBJECT-TYPE    
    SYNTAX DisplayString
	MAX-ACCESS read-only
	STATUS current
    DESCRIPTION
        "Set The link21 R2 Power Status Alarm."
    ::= {link21OBPTrap 23}
	
-- 1.3.6.1.4.1.47477.10.21.21.3.50.24
	link21_powerAlarmR3 	OBJECT-TYPE    
    SYNTAX DisplayString
	MAX-ACCESS read-only
	STATUS current
    DESCRIPTION
        "Set The link21 R3 Power Status Alarm."
    ::= {link21OBPTrap 24}
	
-- 1.3.6.1.4.1.47477.10.21.21.3.50.25
	link21_powerAlarmR4 	OBJECT-TYPE    
    SYNTAX DisplayString
	MAX-ACCESS read-only
	STATUS current
    DESCRIPTION
        "Set The link21 R4 Power Status Alarm."
    ::= {link21OBPTrap 25}
	
	
-- 1.3.6.1.4.1.47477.10.21.21.3.50.26
	link21_powerAlarm1R1 	OBJECT-TYPE    
    SYNTAX DisplayString
	MAX-ACCESS read-only
	STATUS current
    DESCRIPTION
        "Set The link21 1R1 Power Status Alarm."
    ::= {link21OBPTrap 26}
	
-- 1.3.6.1.4.1.47477.10.21.21.3.50.27
	link21_powerAlarm2R1 	OBJECT-TYPE    
    SYNTAX DisplayString
	MAX-ACCESS read-only
	STATUS current
    DESCRIPTION
        "Set The link21 2R1 Power Status Alarm."
    ::= {link21OBPTrap 27}
	
-- 1.3.6.1.4.1.47477.10.21.21.3.50.28
	link21_powerAlarm1R2 	OBJECT-TYPE    
    SYNTAX DisplayString
	MAX-ACCESS read-only
	STATUS current
    DESCRIPTION
        "Set The link21 1R2 Power Status Alarm."
    ::= {link21OBPTrap 28}
	
-- 1.3.6.1.4.1.47477.10.21.21.3.50.29
	link21_powerAlarm2R2 	OBJECT-TYPE    
    SYNTAX DisplayString
	MAX-ACCESS read-only
	STATUS current
    DESCRIPTION
        "Set The link21 2R2 Power Status Alarm."
    ::= {link21OBPTrap 29}
	
-- 1.3.6.1.4.1.47477.10.21.21.3.50.30
	link21_powerAlarm1R3 	OBJECT-TYPE    
    SYNTAX DisplayString
	MAX-ACCESS read-only
	STATUS current
    DESCRIPTION
        "Set The link21 1R3 Power Status Alarm."
    ::= {link21OBPTrap 30}
	
-- 1.3.6.1.4.1.47477.10.21.21.3.50.31
	link21_powerAlarm2R3 	OBJECT-TYPE    
    SYNTAX DisplayString
	MAX-ACCESS read-only
	STATUS current
    DESCRIPTION
        "Set The link21 2R1 Power Status Alarm."
    ::= {link21OBPTrap 31}
	
-- 1.3.6.1.4.1.47477.10.21.21.3.50.32
	link21_powerAlarm1R4 	OBJECT-TYPE    
    SYNTAX DisplayString
	MAX-ACCESS read-only
	STATUS current
    DESCRIPTION
        "Set The link21 1R4 Power Status Alarm."
    ::= {link21OBPTrap 32}
	
-- 1.3.6.1.4.1.47477.10.21.21.3.50.33
	link21_powerAlarm2R4 	OBJECT-TYPE    
    SYNTAX DisplayString
	MAX-ACCESS read-only
	STATUS current
    DESCRIPTION
        "Set The link21 2R4 Power Status Alarm."
    ::= {link21OBPTrap 33}
	
--  1.3.6.1.4.1.47477.10.21.22.3.1
		-- 1.3.6.1.4.1.47477.10.21.22.3.1
		link22_State OBJECT-TYPE
			SYNTAX INTEGER
				{
				off(0),
				on(1)
				}
			MAX-ACCESS read-only
			STATUS current
			DESCRIPTION
				"get the information about whether link22 is working."
			::= { link22OBP 1 }

		
--  1.3.6.1.4.1.47477.10.21.22.3.2
		-- 1.3.6.1.4.1.47477.10.21.22.3.2
		link22_DeviceType OBJECT-TYPE
			SYNTAX DisplayString
			MAX-ACCESS read-only
			STATUS current
			DESCRIPTION
				"get the type of card in link22."
			::= { link22OBP 2 }

			
--  1.3.6.1.4.1.47477.10.21.22.3.3
		-- 1.3.6.1.4.1.47477.10.21.22.3.3
		link22_WorkMode OBJECT-TYPE
			SYNTAX INTEGER
				{
				manualMode(0),
				autoMode(1)
				}
			MAX-ACCESS read-write
			STATUS current
			DESCRIPTION
				"get or set link22's work mode."
			::= { link22OBP 3 }

		
--  1.3.6.1.4.1.47477.10.21.22.3.4
		-- 1.3.6.1.4.1.47477.10.21.22.3.4
		link22_Channel OBJECT-TYPE
			SYNTAX INTEGER
				{
				bypass(0),
				primary(1)
				}
			MAX-ACCESS read-write
			STATUS current
			DESCRIPTION
				"get or set the channel in which link22 works."
			::= { link22OBP 4 }


--  1.3.6.1.4.1.47477.10.21.22.3.5
		-- 1.3.6.1.4.1.47477.10.21.22.3.5
		link22_R1Power OBJECT-TYPE
			SYNTAX DisplayString
			MAX-ACCESS read-only
			STATUS current
			DESCRIPTION
				"get the power of R1 in link22."
			::= { link22OBP 5 }

		
--  1.3.6.1.4.1.47477.10.21.22.3.6
		-- 1.3.6.1.4.1.47477.10.21.22.3.6
		link22_R2Power OBJECT-TYPE
			SYNTAX DisplayString
			MAX-ACCESS read-only
			STATUS current
			DESCRIPTION
				"get the power of R2 in link22."
			::= { link22OBP 6 }
			
--  1.3.6.1.4.1.47477.10.21.22.3.35
		-- 1.3.6.1.4.1.47477.10.21.22.3.35
		link22_R3Power OBJECT-TYPE
			SYNTAX DisplayString
			MAX-ACCESS read-only
			STATUS current
			DESCRIPTION
				"get the power of R3 in link22."
			::= { link22OBP 35 }
			
--  1.3.6.1.4.1.47477.10.21.22.3.36
		-- 1.3.6.1.4.1.47477.10.21.22.3.36
		link22_R4Power OBJECT-TYPE
			SYNTAX DisplayString
			MAX-ACCESS read-only
			STATUS current
			DESCRIPTION
				"get the power of R4 in link22."
			::= { link22OBP 36 }		
		
--  1.3.6.1.4.1.47477.10.21.22.3.7
		-- 1.3.6.1.4.1.47477.10.21.22.3.7
		link22_R1Wave OBJECT-TYPE
			SYNTAX INTEGER
				{
				w1310nm(0),
				w1550nm(1),
				na(2)
				}
			MAX-ACCESS read-write
			STATUS current
			DESCRIPTION
				"get or set the wave length of R1 in link22."
			::= { link22OBP 7 }

		
--  1.3.6.1.4.1.47477.10.21.22.3.8
		-- 1.3.6.1.4.1.47477.10.21.22.3.8
		link22_R2Wave OBJECT-TYPE
			SYNTAX INTEGER
				{
				w1310nm(0),
				w1550nm(1),
				na(2)
				}
			MAX-ACCESS read-write
			STATUS current
			DESCRIPTION
				"get or set the wave length of R2 in link22."
			::= { link22OBP 8 }


--  1.3.6.1.4.1.47477.10.21.22.3.27
		-- 1.3.6.1.4.1.47477.10.21.22.3.27
		link22_R3Wave OBJECT-TYPE
			SYNTAX INTEGER
				{
				w1310nm(0),
				w1550nm(1),
				na(2)
				}
			MAX-ACCESS read-write
			STATUS current
			DESCRIPTION
				"get or set the wave length of R3 in link22."
			::= { link22OBP 27 }

		
--  1.3.6.1.4.1.47477.10.21.22.3.28
		-- 1.3.6.1.4.1.47477.10.21.22.3.28
		link22_R4Wave OBJECT-TYPE
			SYNTAX INTEGER
				{
				w1310nm(0),
				w1550nm(1),
				na(2)
				}
			MAX-ACCESS read-write
			STATUS current
			DESCRIPTION
				"get or set the wave length of R4 in link22."
			::= { link22OBP 28 }
			
--  1.3.6.1.4.1.47477.10.21.22.3.9
		-- 1.3.6.1.4.1.47477.10.21.22.3.9
		link22_R1AlarmPower OBJECT-TYPE
			SYNTAX DisplayString
			MAX-ACCESS read-write
			STATUS current
			DESCRIPTION
				"get or set the power alarm threshold of R1 in link22."
			::= { link22OBP 9 }

		
--  1.3.6.1.4.1.47477.10.21.22.3.10
		-- 1.3.6.1.4.1.47477.10.21.22.3.10
		link22_R2AlarmPower OBJECT-TYPE
			SYNTAX DisplayString
			MAX-ACCESS read-write
			STATUS current
			DESCRIPTION
				"get or set the power alarm threshold of R2 in link22."
			::= { link22OBP 10 }


--  1.3.6.1.4.1.47477.10.21.22.3.29
		-- 1.3.6.1.4.1.47477.10.21.22.3.29
		link22_R3AlarmPower OBJECT-TYPE
			SYNTAX DisplayString
			MAX-ACCESS read-write
			STATUS current
			DESCRIPTION
				"get or set the power alarm threshold of R3 in link22."
			::= { link22OBP 29 }

		
--  1.3.6.1.4.1.47477.10.21.22.3.30
		-- 1.3.6.1.4.1.47477.10.21.22.3.30
		link22_R4AlarmPower OBJECT-TYPE
			SYNTAX DisplayString
			MAX-ACCESS read-write
			STATUS current
			DESCRIPTION
				"get or set the power alarm threshold of R4 in link22."
			::= { link22OBP 30 }

-- OBP4
--  1.3.6.1.4.1.47477.10.21.22.3.37
		-- 1.3.6.1.4.1.47477.10.21.22.3.37
		link22_1R1Power OBJECT-TYPE
			SYNTAX DisplayString
			MAX-ACCESS read-only
			STATUS current
			DESCRIPTION
				"get the power of 1R1 in link22."
			::= { link22OBP 37 }
			
--  1.3.6.1.4.1.47477.10.21.22.3.38
		-- 1.3.6.1.4.1.47477.10.21.22.3.38
		link22_1R2Power OBJECT-TYPE
			SYNTAX DisplayString
			MAX-ACCESS read-only
			STATUS current
			DESCRIPTION
				"get the power of 1R2 in link22."
			::= { link22OBP 38 }

--  1.3.6.1.4.1.47477.10.21.22.3.39
		-- 1.3.6.1.4.1.47477.10.21.22.3.39
		link22_1R3Power OBJECT-TYPE
			SYNTAX DisplayString
			MAX-ACCESS read-only
			STATUS current
			DESCRIPTION
				"get the power of 1R3 in link22."
			::= { link22OBP 39 }
			
--  1.3.6.1.4.1.47477.10.21.22.3.40
		-- 1.3.6.1.4.1.47477.10.21.22.3.40
		link22_1R4Power OBJECT-TYPE
			SYNTAX DisplayString
			MAX-ACCESS read-only
			STATUS current
			DESCRIPTION
				"get the power of 1R4 in link22."
			::= { link22OBP 40 }

--  1.3.6.1.4.1.47477.10.21.22.3.41
		-- 1.3.6.1.4.1.47477.10.21.22.3.41
		link22_2R1Power OBJECT-TYPE
			SYNTAX DisplayString
			MAX-ACCESS read-only
			STATUS current
			DESCRIPTION
				"get the power of 2R1 in link22."
			::= { link22OBP 41 }
			
--  1.3.6.1.4.1.47477.10.21.22.3.42
		-- 1.3.6.1.4.1.47477.10.21.22.3.42
		link22_2R2Power OBJECT-TYPE
			SYNTAX DisplayString
			MAX-ACCESS read-only
			STATUS current
			DESCRIPTION
				"get the power of 2R2 in link22."
			::= { link22OBP 42 }

--  1.3.6.1.4.1.47477.10.21.22.3.41
		-- 1.3.6.1.4.1.47477.10.21.22.3.43
		link22_2R3Power OBJECT-TYPE
			SYNTAX DisplayString
			MAX-ACCESS read-only
			STATUS current
			DESCRIPTION
				"get the power of 2R3 in link22."
			::= { link22OBP 43 }
			
--  1.3.6.1.4.1.47477.10.21.22.3.42
		-- 1.3.6.1.4.1.47477.10.21.22.3.44
		link22_2R4Power OBJECT-TYPE
			SYNTAX DisplayString
			MAX-ACCESS read-only
			STATUS current
			DESCRIPTION
				"get the power of 2R4 in link22."
			::= { link22OBP 44 }
			
--  1.3.6.1.4.1.47477.10.21.22.3.49
		-- 1.3.6.1.4.1.47477.10.21.22.3.49
		link22_1R1Wave OBJECT-TYPE
			SYNTAX INTEGER
				{
				w850nm(0),
				na(2)
				}
			MAX-ACCESS read-only
			STATUS current
			DESCRIPTION
				"get the wave length of 1R1 in link22."
			::= { link22OBP 49 }
		
--  1.3.6.1.4.1.47477.10.21.22.3.60
		-- 1.3.6.1.4.1.47477.10.21.22.3.60
		link22_1R2Wave OBJECT-TYPE
			SYNTAX INTEGER
				{
				w850nm(0),
				na(2)
				}
			MAX-ACCESS read-only
			STATUS current
			DESCRIPTION
				"get the wave length of 1R2 in link22."
			::= { link22OBP 60 }

--  1.3.6.1.4.1.47477.10.21.22.3.61
		-- 1.3.6.1.4.1.47477.10.21.22.3.61
		link22_1R3Wave OBJECT-TYPE
			SYNTAX INTEGER
				{
				w850nm(0),
				na(2)
				}
			MAX-ACCESS read-only
			STATUS current
			DESCRIPTION
				"get the wave length of 1R3 in link22."
			::= { link22OBP 61 }

		
--  1.3.6.1.4.1.47477.10.21.22.3.62
		-- 1.3.6.1.4.1.47477.10.21.22.3.62
		link22_1R4Wave OBJECT-TYPE
			SYNTAX INTEGER
				{
				w850nm(0),
				na(2)
				}
			MAX-ACCESS read-only
			STATUS current
			DESCRIPTION
				"get the wave length of 1R4 in link22."
			::= { link22OBP 62 }
	
--  1.3.6.1.4.1.47477.10.21.22.3.63
		-- 1.3.6.1.4.1.47477.10.21.22.3.63
		link22_2R1Wave OBJECT-TYPE
			SYNTAX INTEGER
				{
				w850nm(0),
				na(2)
				}
			MAX-ACCESS read-only
			STATUS current
			DESCRIPTION
				"get the wave length of 2R1 in link22."
			::= { link22OBP 63 }

		
--  1.3.6.1.4.1.47477.10.21.22.3.64
		-- 1.3.6.1.4.1.47477.10.21.22.3.64
		link22_2R2Wave OBJECT-TYPE
			SYNTAX INTEGER
				{
				w850nm(0),
				na(2)
				}
			MAX-ACCESS read-only
			STATUS current
			DESCRIPTION
				"get the wave length of 2R2 in link22."
			::= { link22OBP 64 }	
	
--  1.3.6.1.4.1.47477.10.21.22.3.65
		-- 1.3.6.1.4.1.47477.10.21.22.3.65
		link22_2R3Wave OBJECT-TYPE
			SYNTAX INTEGER
				{
				w850nm(0),
				na(2)
				}
			MAX-ACCESS read-only
			STATUS current
			DESCRIPTION
				"get the wave length of 2R3 in link22."
			::= { link22OBP 65 }

		
--  1.3.6.1.4.1.47477.10.21.22.3.66
		-- 1.3.6.1.4.1.47477.10.21.22.3.66
		link22_2R4Wave OBJECT-TYPE
			SYNTAX INTEGER
				{
				w850nm(0),
				na(2)
				}
			MAX-ACCESS read-only
			STATUS current
			DESCRIPTION
				"get the wave length of 2R4 in link22."
			::= { link22OBP 66 }	
			
--  1.3.6.1.4.1.47477.10.21.22.3.31
		-- 1.3.6.1.4.1.47477.10.21.22.3.31
		link22_1R1AlarmPower OBJECT-TYPE
			SYNTAX DisplayString
			MAX-ACCESS read-write
			STATUS current
			DESCRIPTION
				"get or set the power alarm threshold of 1R1 in link22."
			::= { link22OBP 31 }
			
--  1.3.6.1.4.1.47477.10.21.22.3.32
		-- 1.3.6.1.4.1.47477.10.21.22.3.32
		link22_1R2AlarmPower OBJECT-TYPE
			SYNTAX DisplayString
			MAX-ACCESS read-write
			STATUS current
			DESCRIPTION
				"get or set the power alarm threshold of 1R2 in link22."
			::= { link22OBP 32 }

--  1.3.6.1.4.1.47477.10.21.22.3.33
		-- 1.3.6.1.4.1.47477.10.21.22.3.33
		link22_1R3AlarmPower OBJECT-TYPE
			SYNTAX DisplayString
			MAX-ACCESS read-write
			STATUS current
			DESCRIPTION
				"get or set the power alarm threshold of 1R3 in link22."
			::= { link22OBP 33 }
			
--  1.3.6.1.4.1.47477.10.21.22.3.34
		-- 1.3.6.1.4.1.47477.10.21.22.3.34
		link22_1R4AlarmPower OBJECT-TYPE
			SYNTAX DisplayString
			MAX-ACCESS read-write
			STATUS current
			DESCRIPTION
				"get or set the power alarm threshold of 1R4 in link22."
			::= { link22OBP 34 }

--  1.3.6.1.4.1.47477.10.21.22.3.45
		-- 1.3.6.1.4.1.47477.10.21.22.3.45
		link22_2R1AlarmPower OBJECT-TYPE
			SYNTAX DisplayString
			MAX-ACCESS read-write
			STATUS current
			DESCRIPTION
				"get or set the power alarm threshold of 2R1 in link22."
			::= { link22OBP 45 }
			
--  1.3.6.1.4.1.47477.10.21.22.3.46
		-- 1.3.6.1.4.1.47477.10.21.22.3.46
		link22_2R2AlarmPower OBJECT-TYPE
			SYNTAX DisplayString
			MAX-ACCESS read-write
			STATUS current
			DESCRIPTION
				"get or set the power alarm threshold of 2R2 in link22."
			::= { link22OBP 46 }

--  1.3.6.1.4.1.47477.10.21.22.3.47
		-- 1.3.6.1.4.1.47477.10.21.22.3.47
		link22_2R3AlarmPower OBJECT-TYPE
			SYNTAX DisplayString
			MAX-ACCESS read-write
			STATUS current
			DESCRIPTION
				"get or set the power alarm threshold of 2R3 in link22."
			::= { link22OBP 47 }
			
--  1.3.6.1.4.1.47477.10.21.22.3.48
		-- 1.3.6.1.4.1.47477.10.21.22.3.48
		link22_2R4AlarmPower OBJECT-TYPE
			SYNTAX DisplayString
			MAX-ACCESS read-write
			STATUS current
			DESCRIPTION
				"get or set the power alarm threshold of 2R4 in link22."
			::= { link22OBP 48 }
			
--  1.3.6.1.4.1.47477.10.21.22.3.11
		-- 1.3.6.1.4.1.47477.10.21.22.3.11
		link22_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link22OBP 11 }
			
--  1.3.6.1.4.1.47477.10.21.22.3.67
		-- 1.3.6.1.4.1.47477.10.21.22.3.67
		link22_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link22OBP 67 }
			
--  1.3.6.1.4.1.47477.10.21.22.3.68
		-- 1.3.6.1.4.1.47477.10.21.22.3.68
		link22_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link22OBP 68 }
			
--  1.3.6.1.4.1.47477.10.21.22.3.12
		-- 1.3.6.1.4.1.47477.10.21.22.3.12
		link22_ReturnDelay OBJECT-TYPE
			--SYNTAX Integer32
			SYNTAX Integer32
			MAX-ACCESS read-write
			STATUS current
			DESCRIPTION
				"get or set how long link22 takes to return to automatic mode."
			::= { link22OBP 12 }
			
--  1.3.6.1.4.1.47477.10.21.22.3.13
		-- 1.3.6.1.4.1.47477.10.21.22.3.13
		link22_BackMode OBJECT-TYPE
			SYNTAX INTEGER
				{
				autoNoBack(0),
				autoBack(1)
				}
			MAX-ACCESS read-write
			STATUS current
			DESCRIPTION
				"get or set the back mode of link22."
			::= { link22OBP 13 }

		
--  1.3.6.1.4.1.47477.10.21.22.3.14
		-- 1.3.6.1.4.1.47477.10.21.22.3.14
		link22_BackDelay OBJECT-TYPE
			SYNTAX Integer32
			MAX-ACCESS read-write
			STATUS current
			DESCRIPTION
				"get or set the back delay."
			::= { link22OBP 14 }

--  1.3.6.1.4.1.47477.10.21.22.3.15
		-- 1.3.6.1.4.1.47477.10.21.22.3.15
		link22_ActiveHeartSwitch OBJECT-TYPE
			SYNTAX INTEGER
				{
				off(0),
				on(1)
				}
			MAX-ACCESS read-write
			STATUS current
			DESCRIPTION
				"get or set the switch status of active heartbeat."
			::= { link22OBP 15 }

		
--  1.3.6.1.4.1.47477.10.21.22.3.16
		-- 1.3.6.1.4.1.47477.10.21.22.3.16
		link22_ActiveSendInterval OBJECT-TYPE
			SYNTAX Integer32
			MAX-ACCESS read-write
			STATUS current
			DESCRIPTION
				"get or set the send interval of active heartbeat."
			::= { link22OBP 16 }		

--  1.3.6.1.4.1.47477.10.21.22.3.17
		-- 1.3.6.1.4.1.47477.10.21.22.3.17
		link22_ActiveTimeOut OBJECT-TYPE
			SYNTAX Integer32
			MAX-ACCESS read-write
			STATUS current
			DESCRIPTION
				"get or set how long the active heartbeat send timeout."
			::= { link22OBP 17 }

--  1.3.6.1.4.1.47477.10.21.22.3.18
		-- 1.3.6.1.4.1.47477.10.21.22.3.18
		link22_ActiveLossBypass OBJECT-TYPE
			SYNTAX Integer32
			MAX-ACCESS read-write
			STATUS current
			DESCRIPTION
				"get or set the bypass for active heartbeat packet loss."
			::= { link22OBP 18 }

--  1.3.6.1.4.1.47477.10.21.22.3.19
		-- 1.3.6.1.4.1.47477.10.21.22.3.19
		link22_PingIpAddress OBJECT-TYPE
			SYNTAX IpAddress
			MAX-ACCESS read-write
			STATUS current
			DESCRIPTION
				"get or set the ping ip address of link22."
			::= { link22OBP 19 }

--  1.3.6.1.4.1.47477.10.21.22.3.20
		-- 1.3.6.1.4.1.47477.10.21.22.3.20
		link22_PassiveHeartSwitch OBJECT-TYPE
			SYNTAX INTEGER
				{
				off(0),
				on(1)
				}
			MAX-ACCESS read-write
			STATUS current
			DESCRIPTION
				"get or set the switch status of passive heartbeat."
			::= { link22OBP 20 }
	

--  1.3.6.1.4.1.47477.10.21.22.3.21
		-- 1.3.6.1.4.1.47477.10.21.22.3.21
		link22_PassiveTimeOut OBJECT-TYPE
			SYNTAX Integer32
			MAX-ACCESS read-write
			STATUS current
			DESCRIPTION
				"get or set how long the passive heartbeat send timeout."
			::= { link22OBP 21 }

--  1.3.6.1.4.1.47477.10.21.22.3.22
		-- 1.3.6.1.4.1.47477.10.21.22.3.22
		link22_PassiveLossBypass OBJECT-TYPE
			SYNTAX Integer32
			MAX-ACCESS read-write
			STATUS current
			DESCRIPTION
				"get or set the bypass for passive heartbeat packet loss."
			::= { link22OBP 22 }

--  1.3.6.1.4.1.47477.10.21.22.3.23
		-- 1.3.6.1.4.1.47477.10.21.22.3.23
		link22_SwitchProtect OBJECT-TYPE
			SYNTAX INTEGER
				{
				off(0),
				on(1)
				}
			MAX-ACCESS read-write
			STATUS current
			DESCRIPTION
				"get or set the switch protection status of link22."
			::= { link22OBP 23 }
			
--  1.3.6.1.4.1.47477.10.21.22.3.24
		-- 1.3.6.1.4.1.47477.10.21.22.3.24
		link22_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link22OBP 24 }		

--  1.3.6.1.4.1.47477.10.21.22.3.25
		-- 1.3.6.1.4.1.47477.10.21.22.3.25
		link22_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link22OBP 25 }	

--  1.3.6.1.4.1.47477.10.21.22.3.26
		-- 1.3.6.1.4.1.47477.10.21.22.3.26
		link22_PowerAlarmStatus OBJECT-TYPE
			SYNTAX INTEGER
				{
				off(0),
				alarm(1),
				normal(2),
				na(3)
				}
			MAX-ACCESS read-only
			STATUS current
			DESCRIPTION
				"get whether a power alarm is generated."
			::= { link22OBP 26 }	


-- 1.3.6.1.4.1.47477.10.21.22.3.50.1
	link22_WorkModeChange 	OBJECT-TYPE    
    SYNTAX INTEGER	{
				manualMode(0),
				autoMode(1)
		}
	MAX-ACCESS read-only
	STATUS current
    DESCRIPTION
        "The Link mode Changed."
    ::= {link22OBPTrap 1}

-- 1.3.6.1.4.1.47477.10.21.22.3.50.2
	link22_StateChange 	OBJECT-TYPE    
    SYNTAX INTEGER	{
				bypass(0),
				primary(1)
		}
	MAX-ACCESS read-only
	STATUS current
    DESCRIPTION
        "The Link State(Channel) Changed."
    ::= {link22OBPTrap 2}

-- 1.3.6.1.4.1.47477.10.21.22.3.50.3
	link22_R1WaveSet 	OBJECT-TYPE    
    SYNTAX INTEGER	{
				w1310nm(0),
				w1550nm(1)
		}
	MAX-ACCESS read-only
	STATUS current
    DESCRIPTION
        "Set The link22 R1 Wave."
    ::= {link22OBPTrap 3}

-- 1.3.6.1.4.1.47477.10.21.22.3.50.4
	link22_R2WaveSet 	OBJECT-TYPE    
    SYNTAX INTEGER	{
				w1310nm(0),
				w1550nm(1)
		}
	MAX-ACCESS read-only
	STATUS current
    DESCRIPTION
        "Set The link22 R2 Wave."
    ::= {link22OBPTrap 4}			

-- 1.3.6.1.4.1.47477.10.21.22.3.50.5
	link22_R3WaveSet 	OBJECT-TYPE    
    SYNTAX INTEGER	{
				w1310nm(0),
				w1550nm(1)
		}
	MAX-ACCESS read-only
	STATUS current
    DESCRIPTION
        "Set The link22 R3 Wave."
    ::= {link22OBPTrap 5}

-- 1.3.6.1.4.1.47477.10.21.22.3.50.6
	link22_R4WaveSet 	OBJECT-TYPE    
    SYNTAX INTEGER	{
				w1310nm(0),
				w1550nm(1)
		}
	MAX-ACCESS read-only
	STATUS current
    DESCRIPTION
        "Set The link22 R4 Wave."
    ::= {link22OBPTrap 6}	
	
-- 1.3.6.1.4.1.47477.10.21.22.3.50.7
	link22_R1AlarmSet 	OBJECT-TYPE    
    SYNTAX DisplayString
	MAX-ACCESS read-only
	STATUS current
    DESCRIPTION
        "Set The link22 R1 Alarm Threshold."
    ::= {link22OBPTrap 7}

-- 1.3.6.1.4.1.47477.10.21.22.3.50.8
	link22_R2AlarmSet 	OBJECT-TYPE    
    SYNTAX DisplayString
	MAX-ACCESS read-only
	STATUS current
    DESCRIPTION
        "Set The link22 R2 Alarm Threshold."
    ::= {link22OBPTrap 8}
	
-- 1.3.6.1.4.1.47477.10.21.22.3.50.9
	link22_R3AlarmSet 	OBJECT-TYPE    
    SYNTAX DisplayString
	MAX-ACCESS read-only
	STATUS current
    DESCRIPTION
        "Set The link22 R3 Alarm Threshold."
    ::= {link22OBPTrap 9}

-- 1.3.6.1.4.1.47477.10.21.22.3.50.10
	link22_R4AlarmSet 	OBJECT-TYPE    
    SYNTAX DisplayString
	MAX-ACCESS read-only
	STATUS current
    DESCRIPTION
        "Set The link22 R4 Alarm Threshold."
    ::= {link22OBPTrap 10}	
	
	
-- 1.3.6.1.4.1.47477.10.21.22.3.50.11
	link22_1R1AlarmSet 	OBJECT-TYPE    
    SYNTAX DisplayString
	MAX-ACCESS read-only
	STATUS current
    DESCRIPTION
        "Set The link22 1R1 Alarm Threshold."
    ::= {link22OBPTrap 11}

-- 1.3.6.1.4.1.47477.10.21.22.3.50.12
	link22_2R1AlarmSet 	OBJECT-TYPE    
    SYNTAX DisplayString
	MAX-ACCESS read-only
	STATUS current
    DESCRIPTION
        "Set The link22 2R1 Alarm Threshold."
    ::= {link22OBPTrap 12}
	
-- 1.3.6.1.4.1.47477.10.21.22.3.50.13
	link22_1R2AlarmSet 	OBJECT-TYPE    
    SYNTAX DisplayString
	MAX-ACCESS read-only
	STATUS current
    DESCRIPTION
        "Set The link22 1R2 Alarm Threshold."
    ::= {link22OBPTrap 13}

-- 1.3.6.1.4.1.47477.10.21.22.3.50.14
	link22_2R2AlarmSet 	OBJECT-TYPE    
    SYNTAX DisplayString
	MAX-ACCESS read-only
	STATUS current
    DESCRIPTION
        "Set The link22 2R2 Alarm Threshold."
    ::= {link22OBPTrap 14}
	
-- 1.3.6.1.4.1.47477.10.21.22.3.50.15
	link22_1R3AlarmSet 	OBJECT-TYPE    
    SYNTAX DisplayString
	MAX-ACCESS read-only
	STATUS current
    DESCRIPTION
        "Set The link22 1R3 Alarm Threshold."
    ::= {link22OBPTrap 15}

-- 1.3.6.1.4.1.47477.10.21.22.3.50.16
	link22_2R3AlarmSet 	OBJECT-TYPE    
    SYNTAX DisplayString
	MAX-ACCESS read-only
	STATUS current
    DESCRIPTION
        "Set The link22 2R3 Alarm Threshold."
    ::= {link22OBPTrap 16}
	
-- 1.3.6.1.4.1.47477.10.21.22.3.50.17
	link22_1R4AlarmSet 	OBJECT-TYPE    
    SYNTAX DisplayString
	MAX-ACCESS read-only
	STATUS current
    DESCRIPTION
        "Set The link22 1R4 Alarm Threshold."
    ::= {link22OBPTrap 17}

-- 1.3.6.1.4.1.47477.10.21.22.3.50.18
	link22_2R4AlarmSet 	OBJECT-TYPE    
    SYNTAX DisplayString
	MAX-ACCESS read-only
	STATUS current
    DESCRIPTION
        "Set The link22 2R4 Alarm Threshold."
    ::= {link22OBPTrap 18}
	
-- 1.3.6.1.4.1.47477.10.21.22.3.50.19
	link22_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link22 PowerAlarmBypass2 Changed."
    ::= {link22OBPTrap 19}
	
-- 1.3.6.1.4.1.47477.10.21.22.3.50.20
	link22_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link22 PowerAlarmBypass4 Changed."
    ::= {link22OBPTrap 20}	
	
-- 1.3.6.1.4.1.47477.10.21.22.3.50.21
	link22_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link22 PowerAlarmBypass8 Changed."
    ::= {link22OBPTrap 21}
	
-- 1.3.6.1.4.1.47477.10.21.22.3.50.22
	link22_powerAlarmR1 	OBJECT-TYPE    
    SYNTAX DisplayString
	MAX-ACCESS read-only
	STATUS current
    DESCRIPTION
        "Set The link22 R1 Power Status Alarm."
    ::= {link22OBPTrap 22}
	
-- 1.3.6.1.4.1.47477.10.21.22.3.50.23
	link22_powerAlarmR2 	OBJECT-TYPE    
    SYNTAX DisplayString
	MAX-ACCESS read-only
	STATUS current
    DESCRIPTION
        "Set The link22 R2 Power Status Alarm."
    ::= {link22OBPTrap 23}
	
-- 1.3.6.1.4.1.47477.10.21.22.3.50.24
	link22_powerAlarmR3 	OBJECT-TYPE    
    SYNTAX DisplayString
	MAX-ACCESS read-only
	STATUS current
    DESCRIPTION
        "Set The link22 R3 Power Status Alarm."
    ::= {link22OBPTrap 24}
	
-- 1.3.6.1.4.1.47477.10.21.22.3.50.25
	link22_powerAlarmR4 	OBJECT-TYPE    
    SYNTAX DisplayString
	MAX-ACCESS read-only
	STATUS current
    DESCRIPTION
        "Set The link22 R4 Power Status Alarm."
    ::= {link22OBPTrap 25}
	
	
-- 1.3.6.1.4.1.47477.10.21.22.3.50.26
	link22_powerAlarm1R1 	OBJECT-TYPE    
    SYNTAX DisplayString
	MAX-ACCESS read-only
	STATUS current
    DESCRIPTION
        "Set The link22 1R1 Power Status Alarm."
    ::= {link22OBPTrap 26}
	
-- 1.3.6.1.4.1.47477.10.21.22.3.50.27
	link22_powerAlarm2R1 	OBJECT-TYPE    
    SYNTAX DisplayString
	MAX-ACCESS read-only
	STATUS current
    DESCRIPTION
        "Set The link22 2R1 Power Status Alarm."
    ::= {link22OBPTrap 27}
	
-- 1.3.6.1.4.1.47477.10.21.22.3.50.28
	link22_powerAlarm1R2 	OBJECT-TYPE    
    SYNTAX DisplayString
	MAX-ACCESS read-only
	STATUS current
    DESCRIPTION
        "Set The link22 1R2 Power Status Alarm."
    ::= {link22OBPTrap 28}
	
-- 1.3.6.1.4.1.47477.10.21.22.3.50.29
	link22_powerAlarm2R2 	OBJECT-TYPE    
    SYNTAX DisplayString
	MAX-ACCESS read-only
	STATUS current
    DESCRIPTION
        "Set The link22 2R2 Power Status Alarm."
    ::= {link22OBPTrap 29}
	
-- 1.3.6.1.4.1.47477.10.21.22.3.50.30
	link22_powerAlarm1R3 	OBJECT-TYPE    
    SYNTAX DisplayString
	MAX-ACCESS read-only
	STATUS current
    DESCRIPTION
        "Set The link22 1R3 Power Status Alarm."
    ::= {link22OBPTrap 30}
	
-- 1.3.6.1.4.1.47477.10.21.22.3.50.31
	link22_powerAlarm2R3 	OBJECT-TYPE    
    SYNTAX DisplayString
	MAX-ACCESS read-only
	STATUS current
    DESCRIPTION
        "Set The link22 2R1 Power Status Alarm."
    ::= {link22OBPTrap 31}
	
-- 1.3.6.1.4.1.47477.10.21.22.3.50.32
	link22_powerAlarm1R4 	OBJECT-TYPE    
    SYNTAX DisplayString
	MAX-ACCESS read-only
	STATUS current
    DESCRIPTION
        "Set The link22 1R4 Power Status Alarm."
    ::= {link22OBPTrap 32}
	
-- 1.3.6.1.4.1.47477.10.21.22.3.50.33
	link22_powerAlarm2R4 	OBJECT-TYPE    
    SYNTAX DisplayString
	MAX-ACCESS read-only
	STATUS current
    DESCRIPTION
        "Set The link22 2R4 Power Status Alarm."
    ::= {link22OBPTrap 33}
	
--  1.3.6.1.4.1.47477.10.21.23.3.1
		-- 1.3.6.1.4.1.47477.10.21.23.3.1
		link23_State OBJECT-TYPE
			SYNTAX INTEGER
				{
				off(0),
				on(1)
				}
			MAX-ACCESS read-only
			STATUS current
			DESCRIPTION
				"get the information about whether link23 is working."
			::= { link23OBP 1 }

		
--  1.3.6.1.4.1.47477.10.21.23.3.2
		-- 1.3.6.1.4.1.47477.10.21.23.3.2
		link23_DeviceType OBJECT-TYPE
			SYNTAX DisplayString
			MAX-ACCESS read-only
			STATUS current
			DESCRIPTION
				"get the type of card in link23."
			::= { link23OBP 2 }

			
--  1.3.6.1.4.1.47477.10.21.23.3.3
		-- 1.3.6.1.4.1.47477.10.21.23.3.3
		link23_WorkMode OBJECT-TYPE
			SYNTAX INTEGER
				{
				manualMode(0),
				autoMode(1)
				}
			MAX-ACCESS read-write
			STATUS current
			DESCRIPTION
				"get or set link23's work mode."
			::= { link23OBP 3 }

		
--  1.3.6.1.4.1.47477.10.21.23.3.4
		-- 1.3.6.1.4.1.47477.10.21.23.3.4
		link23_Channel OBJECT-TYPE
			SYNTAX INTEGER
				{
				bypass(0),
				primary(1)
				}
			MAX-ACCESS read-write
			STATUS current
			DESCRIPTION
				"get or set the channel in which link23 works."
			::= { link23OBP 4 }


--  1.3.6.1.4.1.47477.10.21.23.3.5
		-- 1.3.6.1.4.1.47477.10.21.23.3.5
		link23_R1Power OBJECT-TYPE
			SYNTAX DisplayString
			MAX-ACCESS read-only
			STATUS current
			DESCRIPTION
				"get the power of R1 in link23."
			::= { link23OBP 5 }

		
--  1.3.6.1.4.1.47477.10.21.23.3.6
		-- 1.3.6.1.4.1.47477.10.21.23.3.6
		link23_R2Power OBJECT-TYPE
			SYNTAX DisplayString
			MAX-ACCESS read-only
			STATUS current
			DESCRIPTION
				"get the power of R2 in link23."
			::= { link23OBP 6 }
			
--  1.3.6.1.4.1.47477.10.21.23.3.35
		-- 1.3.6.1.4.1.47477.10.21.23.3.35
		link23_R3Power OBJECT-TYPE
			SYNTAX DisplayString
			MAX-ACCESS read-only
			STATUS current
			DESCRIPTION
				"get the power of R3 in link23."
			::= { link23OBP 35 }
			
--  1.3.6.1.4.1.47477.10.21.23.3.36
		-- 1.3.6.1.4.1.47477.10.21.23.3.36
		link23_R4Power OBJECT-TYPE
			SYNTAX DisplayString
			MAX-ACCESS read-only
			STATUS current
			DESCRIPTION
				"get the power of R4 in link23."
			::= { link23OBP 36 }		
		
--  1.3.6.1.4.1.47477.10.21.23.3.7
		-- 1.3.6.1.4.1.47477.10.21.23.3.7
		link23_R1Wave OBJECT-TYPE
			SYNTAX INTEGER
				{
				w1310nm(0),
				w1550nm(1),
				na(2)
				}
			MAX-ACCESS read-write
			STATUS current
			DESCRIPTION
				"get or set the wave length of R1 in link23."
			::= { link23OBP 7 }

		
--  1.3.6.1.4.1.47477.10.21.23.3.8
		-- 1.3.6.1.4.1.47477.10.21.23.3.8
		link23_R2Wave OBJECT-TYPE
			SYNTAX INTEGER
				{
				w1310nm(0),
				w1550nm(1),
				na(2)
				}
			MAX-ACCESS read-write
			STATUS current
			DESCRIPTION
				"get or set the wave length of R2 in link23."
			::= { link23OBP 8 }


--  1.3.6.1.4.1.47477.10.21.23.3.27
		-- 1.3.6.1.4.1.47477.10.21.23.3.27
		link23_R3Wave OBJECT-TYPE
			SYNTAX INTEGER
				{
				w1310nm(0),
				w1550nm(1),
				na(2)
				}
			MAX-ACCESS read-write
			STATUS current
			DESCRIPTION
				"get or set the wave length of R3 in link23."
			::= { link23OBP 27 }

		
--  1.3.6.1.4.1.47477.10.21.23.3.28
		-- 1.3.6.1.4.1.47477.10.21.23.3.28
		link23_R4Wave OBJECT-TYPE
			SYNTAX INTEGER
				{
				w1310nm(0),
				w1550nm(1),
				na(2)
				}
			MAX-ACCESS read-write
			STATUS current
			DESCRIPTION
				"get or set the wave length of R4 in link23."
			::= { link23OBP 28 }
			
--  1.3.6.1.4.1.47477.10.21.23.3.9
		-- 1.3.6.1.4.1.47477.10.21.23.3.9
		link23_R1AlarmPower OBJECT-TYPE
			SYNTAX DisplayString
			MAX-ACCESS read-write
			STATUS current
			DESCRIPTION
				"get or set the power alarm threshold of R1 in link23."
			::= { link23OBP 9 }

		
--  1.3.6.1.4.1.47477.10.21.23.3.10
		-- 1.3.6.1.4.1.47477.10.21.23.3.10
		link23_R2AlarmPower OBJECT-TYPE
			SYNTAX DisplayString
			MAX-ACCESS read-write
			STATUS current
			DESCRIPTION
				"get or set the power alarm threshold of R2 in link23."
			::= { link23OBP 10 }


--  1.3.6.1.4.1.47477.10.21.23.3.29
		-- 1.3.6.1.4.1.47477.10.21.23.3.29
		link23_R3AlarmPower OBJECT-TYPE
			SYNTAX DisplayString
			MAX-ACCESS read-write
			STATUS current
			DESCRIPTION
				"get or set the power alarm threshold of R3 in link23."
			::= { link23OBP 29 }

		
--  1.3.6.1.4.1.47477.10.21.23.3.30
		-- 1.3.6.1.4.1.47477.10.21.23.3.30
		link23_R4AlarmPower OBJECT-TYPE
			SYNTAX DisplayString
			MAX-ACCESS read-write
			STATUS current
			DESCRIPTION
				"get or set the power alarm threshold of R4 in link23."
			::= { link23OBP 30 }

-- OBP4
--  1.3.6.1.4.1.47477.10.21.23.3.37
		-- 1.3.6.1.4.1.47477.10.21.23.3.37
		link23_1R1Power OBJECT-TYPE
			SYNTAX DisplayString
			MAX-ACCESS read-only
			STATUS current
			DESCRIPTION
				"get the power of 1R1 in link23."
			::= { link23OBP 37 }
			
--  1.3.6.1.4.1.47477.10.21.23.3.38
		-- 1.3.6.1.4.1.47477.10.21.23.3.38
		link23_1R2Power OBJECT-TYPE
			SYNTAX DisplayString
			MAX-ACCESS read-only
			STATUS current
			DESCRIPTION
				"get the power of 1R2 in link23."
			::= { link23OBP 38 }

--  1.3.6.1.4.1.47477.10.21.23.3.39
		-- 1.3.6.1.4.1.47477.10.21.23.3.39
		link23_1R3Power OBJECT-TYPE
			SYNTAX DisplayString
			MAX-ACCESS read-only
			STATUS current
			DESCRIPTION
				"get the power of 1R3 in link23."
			::= { link23OBP 39 }
			
--  1.3.6.1.4.1.47477.10.21.23.3.40
		-- 1.3.6.1.4.1.47477.10.21.23.3.40
		link23_1R4Power OBJECT-TYPE
			SYNTAX DisplayString
			MAX-ACCESS read-only
			STATUS current
			DESCRIPTION
				"get the power of 1R4 in link23."
			::= { link23OBP 40 }

--  1.3.6.1.4.1.47477.10.21.23.3.41
		-- 1.3.6.1.4.1.47477.10.21.23.3.41
		link23_2R1Power OBJECT-TYPE
			SYNTAX DisplayString
			MAX-ACCESS read-only
			STATUS current
			DESCRIPTION
				"get the power of 2R1 in link23."
			::= { link23OBP 41 }
			
--  1.3.6.1.4.1.47477.10.21.23.3.42
		-- 1.3.6.1.4.1.47477.10.21.23.3.42
		link23_2R2Power OBJECT-TYPE
			SYNTAX DisplayString
			MAX-ACCESS read-only
			STATUS current
			DESCRIPTION
				"get the power of 2R2 in link23."
			::= { link23OBP 42 }

--  1.3.6.1.4.1.47477.10.21.23.3.41
		-- 1.3.6.1.4.1.47477.10.21.23.3.43
		link23_2R3Power OBJECT-TYPE
			SYNTAX DisplayString
			MAX-ACCESS read-only
			STATUS current
			DESCRIPTION
				"get the power of 2R3 in link23."
			::= { link23OBP 43 }
			
--  1.3.6.1.4.1.47477.10.21.23.3.42
		-- 1.3.6.1.4.1.47477.10.21.23.3.44
		link23_2R4Power OBJECT-TYPE
			SYNTAX DisplayString
			MAX-ACCESS read-only
			STATUS current
			DESCRIPTION
				"get the power of 2R4 in link23."
			::= { link23OBP 44 }
			
--  1.3.6.1.4.1.47477.10.21.23.3.49
		-- 1.3.6.1.4.1.47477.10.21.23.3.49
		link23_1R1Wave OBJECT-TYPE
			SYNTAX INTEGER
				{
				w850nm(0),
				na(2)
				}
			MAX-ACCESS read-only
			STATUS current
			DESCRIPTION
				"get the wave length of 1R1 in link23."
			::= { link23OBP 49 }
		
--  1.3.6.1.4.1.47477.10.21.23.3.60
		-- 1.3.6.1.4.1.47477.10.21.23.3.60
		link23_1R2Wave OBJECT-TYPE
			SYNTAX INTEGER
				{
				w850nm(0),
				na(2)
				}
			MAX-ACCESS read-only
			STATUS current
			DESCRIPTION
				"get the wave length of 1R2 in link23."
			::= { link23OBP 60 }

--  1.3.6.1.4.1.47477.10.21.23.3.61
		-- 1.3.6.1.4.1.47477.10.21.23.3.61
		link23_1R3Wave OBJECT-TYPE
			SYNTAX INTEGER
				{
				w850nm(0),
				na(2)
				}
			MAX-ACCESS read-only
			STATUS current
			DESCRIPTION
				"get the wave length of 1R3 in link23."
			::= { link23OBP 61 }

		
--  1.3.6.1.4.1.47477.10.21.23.3.62
		-- 1.3.6.1.4.1.47477.10.21.23.3.62
		link23_1R4Wave OBJECT-TYPE
			SYNTAX INTEGER
				{
				w850nm(0),
				na(2)
				}
			MAX-ACCESS read-only
			STATUS current
			DESCRIPTION
				"get the wave length of 1R4 in link23."
			::= { link23OBP 62 }
	
--  1.3.6.1.4.1.47477.10.21.23.3.63
		-- 1.3.6.1.4.1.47477.10.21.23.3.63
		link23_2R1Wave OBJECT-TYPE
			SYNTAX INTEGER
				{
				w850nm(0),
				na(2)
				}
			MAX-ACCESS read-only
			STATUS current
			DESCRIPTION
				"get the wave length of 2R1 in link23."
			::= { link23OBP 63 }

		
--  1.3.6.1.4.1.47477.10.21.23.3.64
		-- 1.3.6.1.4.1.47477.10.21.23.3.64
		link23_2R2Wave OBJECT-TYPE
			SYNTAX INTEGER
				{
				w850nm(0),
				na(2)
				}
			MAX-ACCESS read-only
			STATUS current
			DESCRIPTION
				"get the wave length of 2R2 in link23."
			::= { link23OBP 64 }	
	
--  1.3.6.1.4.1.47477.10.21.23.3.65
		-- 1.3.6.1.4.1.47477.10.21.23.3.65
		link23_2R3Wave OBJECT-TYPE
			SYNTAX INTEGER
				{
				w850nm(0),
				na(2)
				}
			MAX-ACCESS read-only
			STATUS current
			DESCRIPTION
				"get the wave length of 2R3 in link23."
			::= { link23OBP 65 }

		
--  1.3.6.1.4.1.47477.10.21.23.3.66
		-- 1.3.6.1.4.1.47477.10.21.23.3.66
		link23_2R4Wave OBJECT-TYPE
			SYNTAX INTEGER
				{
				w850nm(0),
				na(2)
				}
			MAX-ACCESS read-only
			STATUS current
			DESCRIPTION
				"get the wave length of 2R4 in link23."
			::= { link23OBP 66 }	
			
--  1.3.6.1.4.1.47477.10.21.23.3.31
		-- 1.3.6.1.4.1.47477.10.21.23.3.31
		link23_1R1AlarmPower OBJECT-TYPE
			SYNTAX DisplayString
			MAX-ACCESS read-write
			STATUS current
			DESCRIPTION
				"get or set the power alarm threshold of 1R1 in link23."
			::= { link23OBP 31 }
			
--  1.3.6.1.4.1.47477.10.21.23.3.32
		-- 1.3.6.1.4.1.47477.10.21.23.3.32
		link23_1R2AlarmPower OBJECT-TYPE
			SYNTAX DisplayString
			MAX-ACCESS read-write
			STATUS current
			DESCRIPTION
				"get or set the power alarm threshold of 1R2 in link23."
			::= { link23OBP 32 }

--  1.3.6.1.4.1.47477.10.21.23.3.33
		-- 1.3.6.1.4.1.47477.10.21.23.3.33
		link23_1R3AlarmPower OBJECT-TYPE
			SYNTAX DisplayString
			MAX-ACCESS read-write
			STATUS current
			DESCRIPTION
				"get or set the power alarm threshold of 1R3 in link23."
			::= { link23OBP 33 }
			
--  1.3.6.1.4.1.47477.10.21.23.3.34
		-- 1.3.6.1.4.1.47477.10.21.23.3.34
		link23_1R4AlarmPower OBJECT-TYPE
			SYNTAX DisplayString
			MAX-ACCESS read-write
			STATUS current
			DESCRIPTION
				"get or set the power alarm threshold of 1R4 in link23."
			::= { link23OBP 34 }

--  1.3.6.1.4.1.47477.10.21.23.3.45
		-- 1.3.6.1.4.1.47477.10.21.23.3.45
		link23_2R1AlarmPower OBJECT-TYPE
			SYNTAX DisplayString
			MAX-ACCESS read-write
			STATUS current
			DESCRIPTION
				"get or set the power alarm threshold of 2R1 in link23."
			::= { link23OBP 45 }
			
--  1.3.6.1.4.1.47477.10.21.23.3.46
		-- 1.3.6.1.4.1.47477.10.21.23.3.46
		link23_2R2AlarmPower OBJECT-TYPE
			SYNTAX DisplayString
			MAX-ACCESS read-write
			STATUS current
			DESCRIPTION
				"get or set the power alarm threshold of 2R2 in link23."
			::= { link23OBP 46 }

--  1.3.6.1.4.1.47477.10.21.23.3.47
		-- 1.3.6.1.4.1.47477.10.21.23.3.47
		link23_2R3AlarmPower OBJECT-TYPE
			SYNTAX DisplayString
			MAX-ACCESS read-write
			STATUS current
			DESCRIPTION
				"get or set the power alarm threshold of 2R3 in link23."
			::= { link23OBP 47 }
			
--  1.3.6.1.4.1.47477.10.21.23.3.48
		-- 1.3.6.1.4.1.47477.10.21.23.3.48
		link23_2R4AlarmPower OBJECT-TYPE
			SYNTAX DisplayString
			MAX-ACCESS read-write
			STATUS current
			DESCRIPTION
				"get or set the power alarm threshold of 2R4 in link23."
			::= { link23OBP 48 }
			
--  1.3.6.1.4.1.47477.10.21.23.3.11
		-- 1.3.6.1.4.1.47477.10.21.23.3.11
		link23_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link23OBP 11 }
			
--  1.3.6.1.4.1.47477.10.21.23.3.67
		-- 1.3.6.1.4.1.47477.10.21.23.3.67
		link23_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link23OBP 67 }
			
--  1.3.6.1.4.1.47477.10.21.23.3.68
		-- 1.3.6.1.4.1.47477.10.21.23.3.68
		link23_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link23OBP 68 }
			
--  1.3.6.1.4.1.47477.10.21.23.3.12
		-- 1.3.6.1.4.1.47477.10.21.23.3.12
		link23_ReturnDelay OBJECT-TYPE
			--SYNTAX Integer32
			SYNTAX Integer32
			MAX-ACCESS read-write
			STATUS current
			DESCRIPTION
				"get or set how long link23 takes to return to automatic mode."
			::= { link23OBP 12 }
			
--  1.3.6.1.4.1.47477.10.21.23.3.13
		-- 1.3.6.1.4.1.47477.10.21.23.3.13
		link23_BackMode OBJECT-TYPE
			SYNTAX INTEGER
				{
				autoNoBack(0),
				autoBack(1)
				}
			MAX-ACCESS read-write
			STATUS current
			DESCRIPTION
				"get or set the back mode of link23."
			::= { link23OBP 13 }

		
--  1.3.6.1.4.1.47477.10.21.23.3.14
		-- 1.3.6.1.4.1.47477.10.21.23.3.14
		link23_BackDelay OBJECT-TYPE
			SYNTAX Integer32
			MAX-ACCESS read-write
			STATUS current
			DESCRIPTION
				"get or set the back delay."
			::= { link23OBP 14 }

--  1.3.6.1.4.1.47477.10.21.23.3.15
		-- 1.3.6.1.4.1.47477.10.21.23.3.15
		link23_ActiveHeartSwitch OBJECT-TYPE
			SYNTAX INTEGER
				{
				off(0),
				on(1)
				}
			MAX-ACCESS read-write
			STATUS current
			DESCRIPTION
				"get or set the switch status of active heartbeat."
			::= { link23OBP 15 }

		
--  1.3.6.1.4.1.47477.10.21.23.3.16
		-- 1.3.6.1.4.1.47477.10.21.23.3.16
		link23_ActiveSendInterval OBJECT-TYPE
			SYNTAX Integer32
			MAX-ACCESS read-write
			STATUS current
			DESCRIPTION
				"get or set the send interval of active heartbeat."
			::= { link23OBP 16 }		

--  1.3.6.1.4.1.47477.10.21.23.3.17
		-- 1.3.6.1.4.1.47477.10.21.23.3.17
		link23_ActiveTimeOut OBJECT-TYPE
			SYNTAX Integer32
			MAX-ACCESS read-write
			STATUS current
			DESCRIPTION
				"get or set how long the active heartbeat send timeout."
			::= { link23OBP 17 }

--  1.3.6.1.4.1.47477.10.21.23.3.18
		-- 1.3.6.1.4.1.47477.10.21.23.3.18
		link23_ActiveLossBypass OBJECT-TYPE
			SYNTAX Integer32
			MAX-ACCESS read-write
			STATUS current
			DESCRIPTION
				"get or set the bypass for active heartbeat packet loss."
			::= { link23OBP 18 }

--  1.3.6.1.4.1.47477.10.21.23.3.19
		-- 1.3.6.1.4.1.47477.10.21.23.3.19
		link23_PingIpAddress OBJECT-TYPE
			SYNTAX IpAddress
			MAX-ACCESS read-write
			STATUS current
			DESCRIPTION
				"get or set the ping ip address of link23."
			::= { link23OBP 19 }

--  1.3.6.1.4.1.47477.10.21.23.3.20
		-- 1.3.6.1.4.1.47477.10.21.23.3.20
		link23_PassiveHeartSwitch OBJECT-TYPE
			SYNTAX INTEGER
				{
				off(0),
				on(1)
				}
			MAX-ACCESS read-write
			STATUS current
			DESCRIPTION
				"get or set the switch status of passive heartbeat."
			::= { link23OBP 20 }
	

--  1.3.6.1.4.1.47477.10.21.23.3.21
		-- 1.3.6.1.4.1.47477.10.21.23.3.21
		link23_PassiveTimeOut OBJECT-TYPE
			SYNTAX Integer32
			MAX-ACCESS read-write
			STATUS current
			DESCRIPTION
				"get or set how long the passive heartbeat send timeout."
			::= { link23OBP 21 }

--  1.3.6.1.4.1.47477.10.21.23.3.22
		-- 1.3.6.1.4.1.47477.10.21.23.3.22
		link23_PassiveLossBypass OBJECT-TYPE
			SYNTAX Integer32
			MAX-ACCESS read-write
			STATUS current
			DESCRIPTION
				"get or set the bypass for passive heartbeat packet loss."
			::= { link23OBP 22 }

--  1.3.6.1.4.1.47477.10.21.23.3.23
		-- 1.3.6.1.4.1.47477.10.21.23.3.23
		link23_SwitchProtect OBJECT-TYPE
			SYNTAX INTEGER
				{
				off(0),
				on(1)
				}
			MAX-ACCESS read-write
			STATUS current
			DESCRIPTION
				"get or set the switch protection status of link23."
			::= { link23OBP 23 }
			
--  1.3.6.1.4.1.47477.10.21.23.3.24
		-- 1.3.6.1.4.1.47477.10.21.23.3.24
		link23_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link23OBP 24 }		

--  1.3.6.1.4.1.47477.10.21.23.3.25
		-- 1.3.6.1.4.1.47477.10.21.23.3.25
		link23_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link23OBP 25 }	

--  1.3.6.1.4.1.47477.10.21.23.3.26
		-- 1.3.6.1.4.1.47477.10.21.23.3.26
		link23_PowerAlarmStatus OBJECT-TYPE
			SYNTAX INTEGER
				{
				off(0),
				alarm(1),
				normal(2),
				na(3)
				}
			MAX-ACCESS read-only
			STATUS current
			DESCRIPTION
				"get whether a power alarm is generated."
			::= { link23OBP 26 }	


-- 1.3.6.1.4.1.47477.10.21.23.3.50.1
	link23_WorkModeChange 	OBJECT-TYPE    
    SYNTAX INTEGER	{
				manualMode(0),
				autoMode(1)
		}
	MAX-ACCESS read-only
	STATUS current
    DESCRIPTION
        "The Link mode Changed."
    ::= {link23OBPTrap 1}

-- 1.3.6.1.4.1.47477.10.21.23.3.50.2
	link23_StateChange 	OBJECT-TYPE    
    SYNTAX INTEGER	{
				bypass(0),
				primary(1)
		}
	MAX-ACCESS read-only
	STATUS current
    DESCRIPTION
        "The Link State(Channel) Changed."
    ::= {link23OBPTrap 2}

-- 1.3.6.1.4.1.47477.10.21.23.3.50.3
	link23_R1WaveSet 	OBJECT-TYPE    
    SYNTAX INTEGER	{
				w1310nm(0),
				w1550nm(1)
		}
	MAX-ACCESS read-only
	STATUS current
    DESCRIPTION
        "Set The link23 R1 Wave."
    ::= {link23OBPTrap 3}

-- 1.3.6.1.4.1.47477.10.21.23.3.50.4
	link23_R2WaveSet 	OBJECT-TYPE    
    SYNTAX INTEGER	{
				w1310nm(0),
				w1550nm(1)
		}
	MAX-ACCESS read-only
	STATUS current
    DESCRIPTION
        "Set The link23 R2 Wave."
    ::= {link23OBPTrap 4}			

-- 1.3.6.1.4.1.47477.10.21.23.3.50.5
	link23_R3WaveSet 	OBJECT-TYPE    
    SYNTAX INTEGER	{
				w1310nm(0),
				w1550nm(1)
		}
	MAX-ACCESS read-only
	STATUS current
    DESCRIPTION
        "Set The link23 R3 Wave."
    ::= {link23OBPTrap 5}

-- 1.3.6.1.4.1.47477.10.21.23.3.50.6
	link23_R4WaveSet 	OBJECT-TYPE    
    SYNTAX INTEGER	{
				w1310nm(0),
				w1550nm(1)
		}
	MAX-ACCESS read-only
	STATUS current
    DESCRIPTION
        "Set The link23 R4 Wave."
    ::= {link23OBPTrap 6}	
	
-- 1.3.6.1.4.1.47477.10.21.23.3.50.7
	link23_R1AlarmSet 	OBJECT-TYPE    
    SYNTAX DisplayString
	MAX-ACCESS read-only
	STATUS current
    DESCRIPTION
        "Set The link23 R1 Alarm Threshold."
    ::= {link23OBPTrap 7}

-- 1.3.6.1.4.1.47477.10.21.23.3.50.8
	link23_R2AlarmSet 	OBJECT-TYPE    
    SYNTAX DisplayString
	MAX-ACCESS read-only
	STATUS current
    DESCRIPTION
        "Set The link23 R2 Alarm Threshold."
    ::= {link23OBPTrap 8}
	
-- 1.3.6.1.4.1.47477.10.21.23.3.50.9
	link23_R3AlarmSet 	OBJECT-TYPE    
    SYNTAX DisplayString
	MAX-ACCESS read-only
	STATUS current
    DESCRIPTION
        "Set The link23 R3 Alarm Threshold."
    ::= {link23OBPTrap 9}

-- 1.3.6.1.4.1.47477.10.21.23.3.50.10
	link23_R4AlarmSet 	OBJECT-TYPE    
    SYNTAX DisplayString
	MAX-ACCESS read-only
	STATUS current
    DESCRIPTION
        "Set The link23 R4 Alarm Threshold."
    ::= {link23OBPTrap 10}	
	
	
-- 1.3.6.1.4.1.47477.10.21.23.3.50.11
	link23_1R1AlarmSet 	OBJECT-TYPE    
    SYNTAX DisplayString
	MAX-ACCESS read-only
	STATUS current
    DESCRIPTION
        "Set The link23 1R1 Alarm Threshold."
    ::= {link23OBPTrap 11}

-- 1.3.6.1.4.1.47477.10.21.23.3.50.12
	link23_2R1AlarmSet 	OBJECT-TYPE    
    SYNTAX DisplayString
	MAX-ACCESS read-only
	STATUS current
    DESCRIPTION
        "Set The link23 2R1 Alarm Threshold."
    ::= {link23OBPTrap 12}
	
-- 1.3.6.1.4.1.47477.10.21.23.3.50.13
	link23_1R2AlarmSet 	OBJECT-TYPE    
    SYNTAX DisplayString
	MAX-ACCESS read-only
	STATUS current
    DESCRIPTION
        "Set The link23 1R2 Alarm Threshold."
    ::= {link23OBPTrap 13}

-- 1.3.6.1.4.1.47477.10.21.23.3.50.14
	link23_2R2AlarmSet 	OBJECT-TYPE    
    SYNTAX DisplayString
	MAX-ACCESS read-only
	STATUS current
    DESCRIPTION
        "Set The link23 2R2 Alarm Threshold."
    ::= {link23OBPTrap 14}
	
-- 1.3.6.1.4.1.47477.10.21.23.3.50.15
	link23_1R3AlarmSet 	OBJECT-TYPE    
    SYNTAX DisplayString
	MAX-ACCESS read-only
	STATUS current
    DESCRIPTION
        "Set The link23 1R3 Alarm Threshold."
    ::= {link23OBPTrap 15}

-- 1.3.6.1.4.1.47477.10.21.23.3.50.16
	link23_2R3AlarmSet 	OBJECT-TYPE    
    SYNTAX DisplayString
	MAX-ACCESS read-only
	STATUS current
    DESCRIPTION
        "Set The link23 2R3 Alarm Threshold."
    ::= {link23OBPTrap 16}
	
-- 1.3.6.1.4.1.47477.10.21.23.3.50.17
	link23_1R4AlarmSet 	OBJECT-TYPE    
    SYNTAX DisplayString
	MAX-ACCESS read-only
	STATUS current
    DESCRIPTION
        "Set The link23 1R4 Alarm Threshold."
    ::= {link23OBPTrap 17}

-- 1.3.6.1.4.1.47477.10.21.23.3.50.18
	link23_2R4AlarmSet 	OBJECT-TYPE    
    SYNTAX DisplayString
	MAX-ACCESS read-only
	STATUS current
    DESCRIPTION
        "Set The link23 2R4 Alarm Threshold."
    ::= {link23OBPTrap 18}
	
-- 1.3.6.1.4.1.47477.10.21.23.3.50.19
	link23_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link23 PowerAlarmBypass2 Changed."
    ::= {link23OBPTrap 19}
	
-- 1.3.6.1.4.1.47477.10.21.23.3.50.20
	link23_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link23 PowerAlarmBypass4 Changed."
    ::= {link23OBPTrap 20}	
	
-- 1.3.6.1.4.1.47477.10.21.23.3.50.21
	link23_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link23 PowerAlarmBypass8 Changed."
    ::= {link23OBPTrap 21}
	
-- 1.3.6.1.4.1.47477.10.21.23.3.50.22
	link23_powerAlarmR1 	OBJECT-TYPE    
    SYNTAX DisplayString
	MAX-ACCESS read-only
	STATUS current
    DESCRIPTION
        "Set The link23 R1 Power Status Alarm."
    ::= {link23OBPTrap 22}
	
-- 1.3.6.1.4.1.47477.10.21.23.3.50.23
	link23_powerAlarmR2 	OBJECT-TYPE    
    SYNTAX DisplayString
	MAX-ACCESS read-only
	STATUS current
    DESCRIPTION
        "Set The link23 R2 Power Status Alarm."
    ::= {link23OBPTrap 23}
	
-- 1.3.6.1.4.1.47477.10.21.23.3.50.24
	link23_powerAlarmR3 	OBJECT-TYPE    
    SYNTAX DisplayString
	MAX-ACCESS read-only
	STATUS current
    DESCRIPTION
        "Set The link23 R3 Power Status Alarm."
    ::= {link23OBPTrap 24}
	
-- 1.3.6.1.4.1.47477.10.21.23.3.50.25
	link23_powerAlarmR4 	OBJECT-TYPE    
    SYNTAX DisplayString
	MAX-ACCESS read-only
	STATUS current
    DESCRIPTION
        "Set The link23 R4 Power Status Alarm."
    ::= {link23OBPTrap 25}
	
	
-- 1.3.6.1.4.1.47477.10.21.23.3.50.26
	link23_powerAlarm1R1 	OBJECT-TYPE    
    SYNTAX DisplayString
	MAX-ACCESS read-only
	STATUS current
    DESCRIPTION
        "Set The link23 1R1 Power Status Alarm."
    ::= {link23OBPTrap 26}
	
-- 1.3.6.1.4.1.47477.10.21.23.3.50.27
	link23_powerAlarm2R1 	OBJECT-TYPE    
    SYNTAX DisplayString
	MAX-ACCESS read-only
	STATUS current
    DESCRIPTION
        "Set The link23 2R1 Power Status Alarm."
    ::= {link23OBPTrap 27}
	
-- 1.3.6.1.4.1.47477.10.21.23.3.50.28
	link23_powerAlarm1R2 	OBJECT-TYPE    
    SYNTAX DisplayString
	MAX-ACCESS read-only
	STATUS current
    DESCRIPTION
        "Set The link23 1R2 Power Status Alarm."
    ::= {link23OBPTrap 28}
	
-- 1.3.6.1.4.1.47477.10.21.23.3.50.29
	link23_powerAlarm2R2 	OBJECT-TYPE    
    SYNTAX DisplayString
	MAX-ACCESS read-only
	STATUS current
    DESCRIPTION
        "Set The link23 2R2 Power Status Alarm."
    ::= {link23OBPTrap 29}
	
-- 1.3.6.1.4.1.47477.10.21.23.3.50.30
	link23_powerAlarm1R3 	OBJECT-TYPE    
    SYNTAX DisplayString
	MAX-ACCESS read-only
	STATUS current
    DESCRIPTION
        "Set The link23 1R3 Power Status Alarm."
    ::= {link23OBPTrap 30}
	
-- 1.3.6.1.4.1.47477.10.21.23.3.50.31
	link23_powerAlarm2R3 	OBJECT-TYPE    
    SYNTAX DisplayString
	MAX-ACCESS read-only
	STATUS current
    DESCRIPTION
        "Set The link23 2R1 Power Status Alarm."
    ::= {link23OBPTrap 31}
	
-- 1.3.6.1.4.1.47477.10.21.23.3.50.32
	link23_powerAlarm1R4 	OBJECT-TYPE    
    SYNTAX DisplayString
	MAX-ACCESS read-only
	STATUS current
    DESCRIPTION
        "Set The link23 1R4 Power Status Alarm."
    ::= {link23OBPTrap 32}
	
-- 1.3.6.1.4.1.47477.10.21.23.3.50.33
	link23_powerAlarm2R4 	OBJECT-TYPE    
    SYNTAX DisplayString
	MAX-ACCESS read-only
	STATUS current
    DESCRIPTION
        "Set The link23 2R4 Power Status Alarm."
    ::= {link23OBPTrap 33}
	
--  1.3.6.1.4.1.47477.10.21.24.3.1
		-- 1.3.6.1.4.1.47477.10.21.24.3.1
		link24_State OBJECT-TYPE
			SYNTAX INTEGER
				{
				off(0),
				on(1)
				}
			MAX-ACCESS read-only
			STATUS current
			DESCRIPTION
				"get the information about whether link24 is working."
			::= { link24OBP 1 }

		
--  1.3.6.1.4.1.47477.10.21.24.3.2
		-- 1.3.6.1.4.1.47477.10.21.24.3.2
		link24_DeviceType OBJECT-TYPE
			SYNTAX DisplayString
			MAX-ACCESS read-only
			STATUS current
			DESCRIPTION
				"get the type of card in link24."
			::= { link24OBP 2 }

			
--  1.3.6.1.4.1.47477.10.21.24.3.3
		-- 1.3.6.1.4.1.47477.10.21.24.3.3
		link24_WorkMode OBJECT-TYPE
			SYNTAX INTEGER
				{
				manualMode(0),
				autoMode(1)
				}
			MAX-ACCESS read-write
			STATUS current
			DESCRIPTION
				"get or set link24's work mode."
			::= { link24OBP 3 }

		
--  1.3.6.1.4.1.47477.10.21.24.3.4
		-- 1.3.6.1.4.1.47477.10.21.24.3.4
		link24_Channel OBJECT-TYPE
			SYNTAX INTEGER
				{
				bypass(0),
				primary(1)
				}
			MAX-ACCESS read-write
			STATUS current
			DESCRIPTION
				"get or set the channel in which link24 works."
			::= { link24OBP 4 }


--  1.3.6.1.4.1.47477.10.21.24.3.5
		-- 1.3.6.1.4.1.47477.10.21.24.3.5
		link24_R1Power OBJECT-TYPE
			SYNTAX DisplayString
			MAX-ACCESS read-only
			STATUS current
			DESCRIPTION
				"get the power of R1 in link24."
			::= { link24OBP 5 }

		
--  1.3.6.1.4.1.47477.10.21.24.3.6
		-- 1.3.6.1.4.1.47477.10.21.24.3.6
		link24_R2Power OBJECT-TYPE
			SYNTAX DisplayString
			MAX-ACCESS read-only
			STATUS current
			DESCRIPTION
				"get the power of R2 in link24."
			::= { link24OBP 6 }
			
--  1.3.6.1.4.1.47477.10.21.24.3.35
		-- 1.3.6.1.4.1.47477.10.21.24.3.35
		link24_R3Power OBJECT-TYPE
			SYNTAX DisplayString
			MAX-ACCESS read-only
			STATUS current
			DESCRIPTION
				"get the power of R3 in link24."
			::= { link24OBP 35 }
			
--  1.3.6.1.4.1.47477.10.21.24.3.36
		-- 1.3.6.1.4.1.47477.10.21.24.3.36
		link24_R4Power OBJECT-TYPE
			SYNTAX DisplayString
			MAX-ACCESS read-only
			STATUS current
			DESCRIPTION
				"get the power of R4 in link24."
			::= { link24OBP 36 }		
		
--  1.3.6.1.4.1.47477.10.21.24.3.7
		-- 1.3.6.1.4.1.47477.10.21.24.3.7
		link24_R1Wave OBJECT-TYPE
			SYNTAX INTEGER
				{
				w1310nm(0),
				w1550nm(1),
				na(2)
				}
			MAX-ACCESS read-write
			STATUS current
			DESCRIPTION
				"get or set the wave length of R1 in link24."
			::= { link24OBP 7 }

		
--  1.3.6.1.4.1.47477.10.21.24.3.8
		-- 1.3.6.1.4.1.47477.10.21.24.3.8
		link24_R2Wave OBJECT-TYPE
			SYNTAX INTEGER
				{
				w1310nm(0),
				w1550nm(1),
				na(2)
				}
			MAX-ACCESS read-write
			STATUS current
			DESCRIPTION
				"get or set the wave length of R2 in link24."
			::= { link24OBP 8 }


--  1.3.6.1.4.1.47477.10.21.24.3.27
		-- 1.3.6.1.4.1.47477.10.21.24.3.27
		link24_R3Wave OBJECT-TYPE
			SYNTAX INTEGER
				{
				w1310nm(0),
				w1550nm(1),
				na(2)
				}
			MAX-ACCESS read-write
			STATUS current
			DESCRIPTION
				"get or set the wave length of R3 in link24."
			::= { link24OBP 27 }

		
--  1.3.6.1.4.1.47477.10.21.24.3.28
		-- 1.3.6.1.4.1.47477.10.21.24.3.28
		link24_R4Wave OBJECT-TYPE
			SYNTAX INTEGER
				{
				w1310nm(0),
				w1550nm(1),
				na(2)
				}
			MAX-ACCESS read-write
			STATUS current
			DESCRIPTION
				"get or set the wave length of R4 in link24."
			::= { link24OBP 28 }
			
--  1.3.6.1.4.1.47477.10.21.24.3.9
		-- 1.3.6.1.4.1.47477.10.21.24.3.9
		link24_R1AlarmPower OBJECT-TYPE
			SYNTAX DisplayString
			MAX-ACCESS read-write
			STATUS current
			DESCRIPTION
				"get or set the power alarm threshold of R1 in link24."
			::= { link24OBP 9 }

		
--  1.3.6.1.4.1.47477.10.21.24.3.10
		-- 1.3.6.1.4.1.47477.10.21.24.3.10
		link24_R2AlarmPower OBJECT-TYPE
			SYNTAX DisplayString
			MAX-ACCESS read-write
			STATUS current
			DESCRIPTION
				"get or set the power alarm threshold of R2 in link24."
			::= { link24OBP 10 }


--  1.3.6.1.4.1.47477.10.21.24.3.29
		-- 1.3.6.1.4.1.47477.10.21.24.3.29
		link24_R3AlarmPower OBJECT-TYPE
			SYNTAX DisplayString
			MAX-ACCESS read-write
			STATUS current
			DESCRIPTION
				"get or set the power alarm threshold of R3 in link24."
			::= { link24OBP 29 }

		
--  1.3.6.1.4.1.47477.10.21.24.3.30
		-- 1.3.6.1.4.1.47477.10.21.24.3.30
		link24_R4AlarmPower OBJECT-TYPE
			SYNTAX DisplayString
			MAX-ACCESS read-write
			STATUS current
			DESCRIPTION
				"get or set the power alarm threshold of R4 in link24."
			::= { link24OBP 30 }

-- OBP4
--  1.3.6.1.4.1.47477.10.21.24.3.37
		-- 1.3.6.1.4.1.47477.10.21.24.3.37
		link24_1R1Power OBJECT-TYPE
			SYNTAX DisplayString
			MAX-ACCESS read-only
			STATUS current
			DESCRIPTION
				"get the power of 1R1 in link24."
			::= { link24OBP 37 }
			
--  1.3.6.1.4.1.47477.10.21.24.3.38
		-- 1.3.6.1.4.1.47477.10.21.24.3.38
		link24_1R2Power OBJECT-TYPE
			SYNTAX DisplayString
			MAX-ACCESS read-only
			STATUS current
			DESCRIPTION
				"get the power of 1R2 in link24."
			::= { link24OBP 38 }

--  1.3.6.1.4.1.47477.10.21.24.3.39
		-- 1.3.6.1.4.1.47477.10.21.24.3.39
		link24_1R3Power OBJECT-TYPE
			SYNTAX DisplayString
			MAX-ACCESS read-only
			STATUS current
			DESCRIPTION
				"get the power of 1R3 in link24."
			::= { link24OBP 39 }
			
--  1.3.6.1.4.1.47477.10.21.24.3.40
		-- 1.3.6.1.4.1.47477.10.21.24.3.40
		link24_1R4Power OBJECT-TYPE
			SYNTAX DisplayString
			MAX-ACCESS read-only
			STATUS current
			DESCRIPTION
				"get the power of 1R4 in link24."
			::= { link24OBP 40 }

--  1.3.6.1.4.1.47477.10.21.24.3.41
		-- 1.3.6.1.4.1.47477.10.21.24.3.41
		link24_2R1Power OBJECT-TYPE
			SYNTAX DisplayString
			MAX-ACCESS read-only
			STATUS current
			DESCRIPTION
				"get the power of 2R1 in link24."
			::= { link24OBP 41 }
			
--  1.3.6.1.4.1.47477.10.21.24.3.42
		-- 1.3.6.1.4.1.47477.10.21.24.3.42
		link24_2R2Power OBJECT-TYPE
			SYNTAX DisplayString
			MAX-ACCESS read-only
			STATUS current
			DESCRIPTION
				"get the power of 2R2 in link24."
			::= { link24OBP 42 }

--  1.3.6.1.4.1.47477.10.21.24.3.41
		-- 1.3.6.1.4.1.47477.10.21.24.3.43
		link24_2R3Power OBJECT-TYPE
			SYNTAX DisplayString
			MAX-ACCESS read-only
			STATUS current
			DESCRIPTION
				"get the power of 2R3 in link24."
			::= { link24OBP 43 }
			
--  1.3.6.1.4.1.47477.10.21.24.3.42
		-- 1.3.6.1.4.1.47477.10.21.24.3.44
		link24_2R4Power OBJECT-TYPE
			SYNTAX DisplayString
			MAX-ACCESS read-only
			STATUS current
			DESCRIPTION
				"get the power of 2R4 in link24."
			::= { link24OBP 44 }
			
--  1.3.6.1.4.1.47477.10.21.24.3.49
		-- 1.3.6.1.4.1.47477.10.21.24.3.49
		link24_1R1Wave OBJECT-TYPE
			SYNTAX INTEGER
				{
				w850nm(0),
				na(2)
				}
			MAX-ACCESS read-only
			STATUS current
			DESCRIPTION
				"get the wave length of 1R1 in link24."
			::= { link24OBP 49 }
		
--  1.3.6.1.4.1.47477.10.21.24.3.60
		-- 1.3.6.1.4.1.47477.10.21.24.3.60
		link24_1R2Wave OBJECT-TYPE
			SYNTAX INTEGER
				{
				w850nm(0),
				na(2)
				}
			MAX-ACCESS read-only
			STATUS current
			DESCRIPTION
				"get the wave length of 1R2 in link24."
			::= { link24OBP 60 }

--  1.3.6.1.4.1.47477.10.21.24.3.61
		-- 1.3.6.1.4.1.47477.10.21.24.3.61
		link24_1R3Wave OBJECT-TYPE
			SYNTAX INTEGER
				{
				w850nm(0),
				na(2)
				}
			MAX-ACCESS read-only
			STATUS current
			DESCRIPTION
				"get the wave length of 1R3 in link24."
			::= { link24OBP 61 }

		
--  1.3.6.1.4.1.47477.10.21.24.3.62
		-- 1.3.6.1.4.1.47477.10.21.24.3.62
		link24_1R4Wave OBJECT-TYPE
			SYNTAX INTEGER
				{
				w850nm(0),
				na(2)
				}
			MAX-ACCESS read-only
			STATUS current
			DESCRIPTION
				"get the wave length of 1R4 in link24."
			::= { link24OBP 62 }
	
--  1.3.6.1.4.1.47477.10.21.24.3.63
		-- 1.3.6.1.4.1.47477.10.21.24.3.63
		link24_2R1Wave OBJECT-TYPE
			SYNTAX INTEGER
				{
				w850nm(0),
				na(2)
				}
			MAX-ACCESS read-only
			STATUS current
			DESCRIPTION
				"get the wave length of 2R1 in link24."
			::= { link24OBP 63 }

		
--  1.3.6.1.4.1.47477.10.21.24.3.64
		-- 1.3.6.1.4.1.47477.10.21.24.3.64
		link24_2R2Wave OBJECT-TYPE
			SYNTAX INTEGER
				{
				w850nm(0),
				na(2)
				}
			MAX-ACCESS read-only
			STATUS current
			DESCRIPTION
				"get the wave length of 2R2 in link24."
			::= { link24OBP 64 }	
	
--  1.3.6.1.4.1.47477.10.21.24.3.65
		-- 1.3.6.1.4.1.47477.10.21.24.3.65
		link24_2R3Wave OBJECT-TYPE
			SYNTAX INTEGER
				{
				w850nm(0),
				na(2)
				}
			MAX-ACCESS read-only
			STATUS current
			DESCRIPTION
				"get the wave length of 2R3 in link24."
			::= { link24OBP 65 }

		
--  1.3.6.1.4.1.47477.10.21.24.3.66
		-- 1.3.6.1.4.1.47477.10.21.24.3.66
		link24_2R4Wave OBJECT-TYPE
			SYNTAX INTEGER
				{
				w850nm(0),
				na(2)
				}
			MAX-ACCESS read-only
			STATUS current
			DESCRIPTION
				"get the wave length of 2R4 in link24."
			::= { link24OBP 66 }	
			
--  1.3.6.1.4.1.47477.10.21.24.3.31
		-- 1.3.6.1.4.1.47477.10.21.24.3.31
		link24_1R1AlarmPower OBJECT-TYPE
			SYNTAX DisplayString
			MAX-ACCESS read-write
			STATUS current
			DESCRIPTION
				"get or set the power alarm threshold of 1R1 in link24."
			::= { link24OBP 31 }
			
--  1.3.6.1.4.1.47477.10.21.24.3.32
		-- 1.3.6.1.4.1.47477.10.21.24.3.32
		link24_1R2AlarmPower OBJECT-TYPE
			SYNTAX DisplayString
			MAX-ACCESS read-write
			STATUS current
			DESCRIPTION
				"get or set the power alarm threshold of 1R2 in link24."
			::= { link24OBP 32 }

--  1.3.6.1.4.1.47477.10.21.24.3.33
		-- 1.3.6.1.4.1.47477.10.21.24.3.33
		link24_1R3AlarmPower OBJECT-TYPE
			SYNTAX DisplayString
			MAX-ACCESS read-write
			STATUS current
			DESCRIPTION
				"get or set the power alarm threshold of 1R3 in link24."
			::= { link24OBP 33 }
			
--  1.3.6.1.4.1.47477.10.21.24.3.34
		-- 1.3.6.1.4.1.47477.10.21.24.3.34
		link24_1R4AlarmPower OBJECT-TYPE
			SYNTAX DisplayString
			MAX-ACCESS read-write
			STATUS current
			DESCRIPTION
				"get or set the power alarm threshold of 1R4 in link24."
			::= { link24OBP 34 }

--  1.3.6.1.4.1.47477.10.21.24.3.45
		-- 1.3.6.1.4.1.47477.10.21.24.3.45
		link24_2R1AlarmPower OBJECT-TYPE
			SYNTAX DisplayString
			MAX-ACCESS read-write
			STATUS current
			DESCRIPTION
				"get or set the power alarm threshold of 2R1 in link24."
			::= { link24OBP 45 }
			
--  1.3.6.1.4.1.47477.10.21.24.3.46
		-- 1.3.6.1.4.1.47477.10.21.24.3.46
		link24_2R2AlarmPower OBJECT-TYPE
			SYNTAX DisplayString
			MAX-ACCESS read-write
			STATUS current
			DESCRIPTION
				"get or set the power alarm threshold of 2R2 in link24."
			::= { link24OBP 46 }

--  1.3.6.1.4.1.47477.10.21.24.3.47
		-- 1.3.6.1.4.1.47477.10.21.24.3.47
		link24_2R3AlarmPower OBJECT-TYPE
			SYNTAX DisplayString
			MAX-ACCESS read-write
			STATUS current
			DESCRIPTION
				"get or set the power alarm threshold of 2R3 in link24."
			::= { link24OBP 47 }
			
--  1.3.6.1.4.1.47477.10.21.24.3.48
		-- 1.3.6.1.4.1.47477.10.21.24.3.48
		link24_2R4AlarmPower OBJECT-TYPE
			SYNTAX DisplayString
			MAX-ACCESS read-write
			STATUS current
			DESCRIPTION
				"get or set the power alarm threshold of 2R4 in link24."
			::= { link24OBP 48 }
			
--  1.3.6.1.4.1.47477.10.21.24.3.11
		-- 1.3.6.1.4.1.47477.10.21.24.3.11
		link24_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link24OBP 11 }
			
--  1.3.6.1.4.1.47477.10.21.24.3.67
		-- 1.3.6.1.4.1.47477.10.21.24.3.67
		link24_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link24OBP 67 }
			
--  1.3.6.1.4.1.47477.10.21.24.3.68
		-- 1.3.6.1.4.1.47477.10.21.24.3.68
		link24_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link24OBP 68 }
			
--  1.3.6.1.4.1.47477.10.21.24.3.12
		-- 1.3.6.1.4.1.47477.10.21.24.3.12
		link24_ReturnDelay OBJECT-TYPE
			--SYNTAX Integer32
			SYNTAX Integer32
			MAX-ACCESS read-write
			STATUS current
			DESCRIPTION
				"get or set how long link24 takes to return to automatic mode."
			::= { link24OBP 12 }
			
--  1.3.6.1.4.1.47477.10.21.24.3.13
		-- 1.3.6.1.4.1.47477.10.21.24.3.13
		link24_BackMode OBJECT-TYPE
			SYNTAX INTEGER
				{
				autoNoBack(0),
				autoBack(1)
				}
			MAX-ACCESS read-write
			STATUS current
			DESCRIPTION
				"get or set the back mode of link24."
			::= { link24OBP 13 }

		
--  1.3.6.1.4.1.47477.10.21.24.3.14
		-- 1.3.6.1.4.1.47477.10.21.24.3.14
		link24_BackDelay OBJECT-TYPE
			SYNTAX Integer32
			MAX-ACCESS read-write
			STATUS current
			DESCRIPTION
				"get or set the back delay."
			::= { link24OBP 14 }

--  1.3.6.1.4.1.47477.10.21.24.3.15
		-- 1.3.6.1.4.1.47477.10.21.24.3.15
		link24_ActiveHeartSwitch OBJECT-TYPE
			SYNTAX INTEGER
				{
				off(0),
				on(1)
				}
			MAX-ACCESS read-write
			STATUS current
			DESCRIPTION
				"get or set the switch status of active heartbeat."
			::= { link24OBP 15 }

		
--  1.3.6.1.4.1.47477.10.21.24.3.16
		-- 1.3.6.1.4.1.47477.10.21.24.3.16
		link24_ActiveSendInterval OBJECT-TYPE
			SYNTAX Integer32
			MAX-ACCESS read-write
			STATUS current
			DESCRIPTION
				"get or set the send interval of active heartbeat."
			::= { link24OBP 16 }		

--  1.3.6.1.4.1.47477.10.21.24.3.17
		-- 1.3.6.1.4.1.47477.10.21.24.3.17
		link24_ActiveTimeOut OBJECT-TYPE
			SYNTAX Integer32
			MAX-ACCESS read-write
			STATUS current
			DESCRIPTION
				"get or set how long the active heartbeat send timeout."
			::= { link24OBP 17 }

--  1.3.6.1.4.1.47477.10.21.24.3.18
		-- 1.3.6.1.4.1.47477.10.21.24.3.18
		link24_ActiveLossBypass OBJECT-TYPE
			SYNTAX Integer32
			MAX-ACCESS read-write
			STATUS current
			DESCRIPTION
				"get or set the bypass for active heartbeat packet loss."
			::= { link24OBP 18 }

--  1.3.6.1.4.1.47477.10.21.24.3.19
		-- 1.3.6.1.4.1.47477.10.21.24.3.19
		link24_PingIpAddress OBJECT-TYPE
			SYNTAX IpAddress
			MAX-ACCESS read-write
			STATUS current
			DESCRIPTION
				"get or set the ping ip address of link24."
			::= { link24OBP 19 }

--  1.3.6.1.4.1.47477.10.21.24.3.20
		-- 1.3.6.1.4.1.47477.10.21.24.3.20
		link24_PassiveHeartSwitch OBJECT-TYPE
			SYNTAX INTEGER
				{
				off(0),
				on(1)
				}
			MAX-ACCESS read-write
			STATUS current
			DESCRIPTION
				"get or set the switch status of passive heartbeat."
			::= { link24OBP 20 }
	

--  1.3.6.1.4.1.47477.10.21.24.3.21
		-- 1.3.6.1.4.1.47477.10.21.24.3.21
		link24_PassiveTimeOut OBJECT-TYPE
			SYNTAX Integer32
			MAX-ACCESS read-write
			STATUS current
			DESCRIPTION
				"get or set how long the passive heartbeat send timeout."
			::= { link24OBP 21 }

--  1.3.6.1.4.1.47477.10.21.24.3.22
		-- 1.3.6.1.4.1.47477.10.21.24.3.22
		link24_PassiveLossBypass OBJECT-TYPE
			SYNTAX Integer32
			MAX-ACCESS read-write
			STATUS current
			DESCRIPTION
				"get or set the bypass for passive heartbeat packet loss."
			::= { link24OBP 22 }

--  1.3.6.1.4.1.47477.10.21.24.3.23
		-- 1.3.6.1.4.1.47477.10.21.24.3.23
		link24_SwitchProtect OBJECT-TYPE
			SYNTAX INTEGER
				{
				off(0),
				on(1)
				}
			MAX-ACCESS read-write
			STATUS current
			DESCRIPTION
				"get or set the switch protection status of link24."
			::= { link24OBP 23 }
			
--  1.3.6.1.4.1.47477.10.21.24.3.24
		-- 1.3.6.1.4.1.47477.10.21.24.3.24
		link24_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link24OBP 24 }		

--  1.3.6.1.4.1.47477.10.21.24.3.25
		-- 1.3.6.1.4.1.47477.10.21.24.3.25
		link24_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link24OBP 25 }	

--  1.3.6.1.4.1.47477.10.21.24.3.26
		-- 1.3.6.1.4.1.47477.10.21.24.3.26
		link24_PowerAlarmStatus OBJECT-TYPE
			SYNTAX INTEGER
				{
				off(0),
				alarm(1),
				normal(2),
				na(3)
				}
			MAX-ACCESS read-only
			STATUS current
			DESCRIPTION
				"get whether a power alarm is generated."
			::= { link24OBP 26 }	


-- 1.3.6.1.4.1.47477.10.21.24.3.50.1
	link24_WorkModeChange 	OBJECT-TYPE    
    SYNTAX INTEGER	{
				manualMode(0),
				autoMode(1)
		}
	MAX-ACCESS read-only
	STATUS current
    DESCRIPTION
        "The Link mode Changed."
    ::= {link24OBPTrap 1}

-- 1.3.6.1.4.1.47477.10.21.24.3.50.2
	link24_StateChange 	OBJECT-TYPE    
    SYNTAX INTEGER	{
				bypass(0),
				primary(1)
		}
	MAX-ACCESS read-only
	STATUS current
    DESCRIPTION
        "The Link State(Channel) Changed."
    ::= {link24OBPTrap 2}

-- 1.3.6.1.4.1.47477.10.21.24.3.50.3
	link24_R1WaveSet 	OBJECT-TYPE    
    SYNTAX INTEGER	{
				w1310nm(0),
				w1550nm(1)
		}
	MAX-ACCESS read-only
	STATUS current
    DESCRIPTION
        "Set The link24 R1 Wave."
    ::= {link24OBPTrap 3}

-- 1.3.6.1.4.1.47477.10.21.24.3.50.4
	link24_R2WaveSet 	OBJECT-TYPE    
    SYNTAX INTEGER	{
				w1310nm(0),
				w1550nm(1)
		}
	MAX-ACCESS read-only
	STATUS current
    DESCRIPTION
        "Set The link24 R2 Wave."
    ::= {link24OBPTrap 4}			

-- 1.3.6.1.4.1.47477.10.21.24.3.50.5
	link24_R3WaveSet 	OBJECT-TYPE    
    SYNTAX INTEGER	{
				w1310nm(0),
				w1550nm(1)
		}
	MAX-ACCESS read-only
	STATUS current
    DESCRIPTION
        "Set The link24 R3 Wave."
    ::= {link24OBPTrap 5}

-- 1.3.6.1.4.1.47477.10.21.24.3.50.6
	link24_R4WaveSet 	OBJECT-TYPE    
    SYNTAX INTEGER	{
				w1310nm(0),
				w1550nm(1)
		}
	MAX-ACCESS read-only
	STATUS current
    DESCRIPTION
        "Set The link24 R4 Wave."
    ::= {link24OBPTrap 6}	
	
-- 1.3.6.1.4.1.47477.10.21.24.3.50.7
	link24_R1AlarmSet 	OBJECT-TYPE    
    SYNTAX DisplayString
	MAX-ACCESS read-only
	STATUS current
    DESCRIPTION
        "Set The link24 R1 Alarm Threshold."
    ::= {link24OBPTrap 7}

-- 1.3.6.1.4.1.47477.10.21.24.3.50.8
	link24_R2AlarmSet 	OBJECT-TYPE    
    SYNTAX DisplayString
	MAX-ACCESS read-only
	STATUS current
    DESCRIPTION
        "Set The link24 R2 Alarm Threshold."
    ::= {link24OBPTrap 8}
	
-- 1.3.6.1.4.1.47477.10.21.24.3.50.9
	link24_R3AlarmSet 	OBJECT-TYPE    
    SYNTAX DisplayString
	MAX-ACCESS read-only
	STATUS current
    DESCRIPTION
        "Set The link24 R3 Alarm Threshold."
    ::= {link24OBPTrap 9}

-- 1.3.6.1.4.1.47477.10.21.24.3.50.10
	link24_R4AlarmSet 	OBJECT-TYPE    
    SYNTAX DisplayString
	MAX-ACCESS read-only
	STATUS current
    DESCRIPTION
        "Set The link24 R4 Alarm Threshold."
    ::= {link24OBPTrap 10}	
	
	
-- 1.3.6.1.4.1.47477.10.21.24.3.50.11
	link24_1R1AlarmSet 	OBJECT-TYPE    
    SYNTAX DisplayString
	MAX-ACCESS read-only
	STATUS current
    DESCRIPTION
        "Set The link24 1R1 Alarm Threshold."
    ::= {link24OBPTrap 11}

-- 1.3.6.1.4.1.47477.10.21.24.3.50.12
	link24_2R1AlarmSet 	OBJECT-TYPE    
    SYNTAX DisplayString
	MAX-ACCESS read-only
	STATUS current
    DESCRIPTION
        "Set The link24 2R1 Alarm Threshold."
    ::= {link24OBPTrap 12}
	
-- 1.3.6.1.4.1.47477.10.21.24.3.50.13
	link24_1R2AlarmSet 	OBJECT-TYPE    
    SYNTAX DisplayString
	MAX-ACCESS read-only
	STATUS current
    DESCRIPTION
        "Set The link24 1R2 Alarm Threshold."
    ::= {link24OBPTrap 13}

-- 1.3.6.1.4.1.47477.10.21.24.3.50.14
	link24_2R2AlarmSet 	OBJECT-TYPE    
    SYNTAX DisplayString
	MAX-ACCESS read-only
	STATUS current
    DESCRIPTION
        "Set The link24 2R2 Alarm Threshold."
    ::= {link24OBPTrap 14}
	
-- 1.3.6.1.4.1.47477.10.21.24.3.50.15
	link24_1R3AlarmSet 	OBJECT-TYPE    
    SYNTAX DisplayString
	MAX-ACCESS read-only
	STATUS current
    DESCRIPTION
        "Set The link24 1R3 Alarm Threshold."
    ::= {link24OBPTrap 15}

-- 1.3.6.1.4.1.47477.10.21.24.3.50.16
	link24_2R3AlarmSet 	OBJECT-TYPE    
    SYNTAX DisplayString
	MAX-ACCESS read-only
	STATUS current
    DESCRIPTION
        "Set The link24 2R3 Alarm Threshold."
    ::= {link24OBPTrap 16}
	
-- 1.3.6.1.4.1.47477.10.21.24.3.50.17
	link24_1R4AlarmSet 	OBJECT-TYPE    
    SYNTAX DisplayString
	MAX-ACCESS read-only
	STATUS current
    DESCRIPTION
        "Set The link24 1R4 Alarm Threshold."
    ::= {link24OBPTrap 17}

-- 1.3.6.1.4.1.47477.10.21.24.3.50.18
	link24_2R4AlarmSet 	OBJECT-TYPE    
    SYNTAX DisplayString
	MAX-ACCESS read-only
	STATUS current
    DESCRIPTION
        "Set The link24 2R4 Alarm Threshold."
    ::= {link24OBPTrap 18}
	
-- 1.3.6.1.4.1.47477.10.21.24.3.50.19
	link24_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link24 PowerAlarmBypass2 Changed."
    ::= {link24OBPTrap 19}
	
-- 1.3.6.1.4.1.47477.10.21.24.3.50.20
	link24_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link24 PowerAlarmBypass4 Changed."
    ::= {link24OBPTrap 20}	
	
-- 1.3.6.1.4.1.47477.10.21.24.3.50.21
	link24_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link24 PowerAlarmBypass8 Changed."
    ::= {link24OBPTrap 21}
	
-- 1.3.6.1.4.1.47477.10.21.24.3.50.22
	link24_powerAlarmR1 	OBJECT-TYPE    
    SYNTAX DisplayString
	MAX-ACCESS read-only
	STATUS current
    DESCRIPTION
        "Set The link24 R1 Power Status Alarm."
    ::= {link24OBPTrap 22}
	
-- 1.3.6.1.4.1.47477.10.21.24.3.50.23
	link24_powerAlarmR2 	OBJECT-TYPE    
    SYNTAX DisplayString
	MAX-ACCESS read-only
	STATUS current
    DESCRIPTION
        "Set The link24 R2 Power Status Alarm."
    ::= {link24OBPTrap 23}
	
-- 1.3.6.1.4.1.47477.10.21.24.3.50.24
	link24_powerAlarmR3 	OBJECT-TYPE    
    SYNTAX DisplayString
	MAX-ACCESS read-only
	STATUS current
    DESCRIPTION
        "Set The link24 R3 Power Status Alarm."
    ::= {link24OBPTrap 24}
	
-- 1.3.6.1.4.1.47477.10.21.24.3.50.25
	link24_powerAlarmR4 	OBJECT-TYPE    
    SYNTAX DisplayString
	MAX-ACCESS read-only
	STATUS current
    DESCRIPTION
        "Set The link24 R4 Power Status Alarm."
    ::= {link24OBPTrap 25}
	
	
-- 1.3.6.1.4.1.47477.10.21.24.3.50.26
	link24_powerAlarm1R1 	OBJECT-TYPE    
    SYNTAX DisplayString
	MAX-ACCESS read-only
	STATUS current
    DESCRIPTION
        "Set The link24 1R1 Power Status Alarm."
    ::= {link24OBPTrap 26}
	
-- 1.3.6.1.4.1.47477.10.21.24.3.50.27
	link24_powerAlarm2R1 	OBJECT-TYPE    
    SYNTAX DisplayString
	MAX-ACCESS read-only
	STATUS current
    DESCRIPTION
        "Set The link24 2R1 Power Status Alarm."
    ::= {link24OBPTrap 27}
	
-- 1.3.6.1.4.1.47477.10.21.24.3.50.28
	link24_powerAlarm1R2 	OBJECT-TYPE    
    SYNTAX DisplayString
	MAX-ACCESS read-only
	STATUS current
    DESCRIPTION
        "Set The link24 1R2 Power Status Alarm."
    ::= {link24OBPTrap 28}
	
-- 1.3.6.1.4.1.47477.10.21.24.3.50.29
	link24_powerAlarm2R2 	OBJECT-TYPE    
    SYNTAX DisplayString
	MAX-ACCESS read-only
	STATUS current
    DESCRIPTION
        "Set The link24 2R2 Power Status Alarm."
    ::= {link24OBPTrap 29}
	
-- 1.3.6.1.4.1.47477.10.21.24.3.50.30
	link24_powerAlarm1R3 	OBJECT-TYPE    
    SYNTAX DisplayString
	MAX-ACCESS read-only
	STATUS current
    DESCRIPTION
        "Set The link24 1R3 Power Status Alarm."
    ::= {link24OBPTrap 30}
	
-- 1.3.6.1.4.1.47477.10.21.24.3.50.31
	link24_powerAlarm2R3 	OBJECT-TYPE    
    SYNTAX DisplayString
	MAX-ACCESS read-only
	STATUS current
    DESCRIPTION
        "Set The link24 2R1 Power Status Alarm."
    ::= {link24OBPTrap 31}
	
-- 1.3.6.1.4.1.47477.10.21.24.3.50.32
	link24_powerAlarm1R4 	OBJECT-TYPE    
    SYNTAX DisplayString
	MAX-ACCESS read-only
	STATUS current
    DESCRIPTION
        "Set The link24 1R4 Power Status Alarm."
    ::= {link24OBPTrap 32}
	
-- 1.3.6.1.4.1.47477.10.21.24.3.50.33
	link24_powerAlarm2R4 	OBJECT-TYPE    
    SYNTAX DisplayString
	MAX-ACCESS read-only
	STATUS current
    DESCRIPTION
        "Set The link24 2R4 Power Status Alarm."
    ::= {link24OBPTrap 33}
	
--  1.3.6.1.4.1.47477.10.21.25.3.1
		-- 1.3.6.1.4.1.47477.10.21.25.3.1
		link25_State OBJECT-TYPE
			SYNTAX INTEGER
				{
				off(0),
				on(1)
				}
			MAX-ACCESS read-only
			STATUS current
			DESCRIPTION
				"get the information about whether link25 is working."
			::= { link25OBP 1 }

		
--  1.3.6.1.4.1.47477.10.21.25.3.2
		-- 1.3.6.1.4.1.47477.10.21.25.3.2
		link25_DeviceType OBJECT-TYPE
			SYNTAX DisplayString
			MAX-ACCESS read-only
			STATUS current
			DESCRIPTION
				"get the type of card in link25."
			::= { link25OBP 2 }

			
--  1.3.6.1.4.1.47477.10.21.25.3.3
		-- 1.3.6.1.4.1.47477.10.21.25.3.3
		link25_WorkMode OBJECT-TYPE
			SYNTAX INTEGER
				{
				manualMode(0),
				autoMode(1)
				}
			MAX-ACCESS read-write
			STATUS current
			DESCRIPTION
				"get or set link25's work mode."
			::= { link25OBP 3 }

		
--  1.3.6.1.4.1.47477.10.21.25.3.4
		-- 1.3.6.1.4.1.47477.10.21.25.3.4
		link25_Channel OBJECT-TYPE
			SYNTAX INTEGER
				{
				bypass(0),
				primary(1)
				}
			MAX-ACCESS read-write
			STATUS current
			DESCRIPTION
				"get or set the channel in which link25 works."
			::= { link25OBP 4 }


--  1.3.6.1.4.1.47477.10.21.25.3.5
		-- 1.3.6.1.4.1.47477.10.21.25.3.5
		link25_R1Power OBJECT-TYPE
			SYNTAX DisplayString
			MAX-ACCESS read-only
			STATUS current
			DESCRIPTION
				"get the power of R1 in link25."
			::= { link25OBP 5 }

		
--  1.3.6.1.4.1.47477.10.21.25.3.6
		-- 1.3.6.1.4.1.47477.10.21.25.3.6
		link25_R2Power OBJECT-TYPE
			SYNTAX DisplayString
			MAX-ACCESS read-only
			STATUS current
			DESCRIPTION
				"get the power of R2 in link25."
			::= { link25OBP 6 }
			
--  1.3.6.1.4.1.47477.10.21.25.3.35
		-- 1.3.6.1.4.1.47477.10.21.25.3.35
		link25_R3Power OBJECT-TYPE
			SYNTAX DisplayString
			MAX-ACCESS read-only
			STATUS current
			DESCRIPTION
				"get the power of R3 in link25."
			::= { link25OBP 35 }
			
--  1.3.6.1.4.1.47477.10.21.25.3.36
		-- 1.3.6.1.4.1.47477.10.21.25.3.36
		link25_R4Power OBJECT-TYPE
			SYNTAX DisplayString
			MAX-ACCESS read-only
			STATUS current
			DESCRIPTION
				"get the power of R4 in link25."
			::= { link25OBP 36 }		
		
--  1.3.6.1.4.1.47477.10.21.25.3.7
		-- 1.3.6.1.4.1.47477.10.21.25.3.7
		link25_R1Wave OBJECT-TYPE
			SYNTAX INTEGER
				{
				w1310nm(0),
				w1550nm(1),
				na(2)
				}
			MAX-ACCESS read-write
			STATUS current
			DESCRIPTION
				"get or set the wave length of R1 in link25."
			::= { link25OBP 7 }

		
--  1.3.6.1.4.1.47477.10.21.25.3.8
		-- 1.3.6.1.4.1.47477.10.21.25.3.8
		link25_R2Wave OBJECT-TYPE
			SYNTAX INTEGER
				{
				w1310nm(0),
				w1550nm(1),
				na(2)
				}
			MAX-ACCESS read-write
			STATUS current
			DESCRIPTION
				"get or set the wave length of R2 in link25."
			::= { link25OBP 8 }


--  1.3.6.1.4.1.47477.10.21.25.3.27
		-- 1.3.6.1.4.1.47477.10.21.25.3.27
		link25_R3Wave OBJECT-TYPE
			SYNTAX INTEGER
				{
				w1310nm(0),
				w1550nm(1),
				na(2)
				}
			MAX-ACCESS read-write
			STATUS current
			DESCRIPTION
				"get or set the wave length of R3 in link25."
			::= { link25OBP 27 }

		
--  1.3.6.1.4.1.47477.10.21.25.3.28
		-- 1.3.6.1.4.1.47477.10.21.25.3.28
		link25_R4Wave OBJECT-TYPE
			SYNTAX INTEGER
				{
				w1310nm(0),
				w1550nm(1),
				na(2)
				}
			MAX-ACCESS read-write
			STATUS current
			DESCRIPTION
				"get or set the wave length of R4 in link25."
			::= { link25OBP 28 }
			
--  1.3.6.1.4.1.47477.10.21.25.3.9
		-- 1.3.6.1.4.1.47477.10.21.25.3.9
		link25_R1AlarmPower OBJECT-TYPE
			SYNTAX DisplayString
			MAX-ACCESS read-write
			STATUS current
			DESCRIPTION
				"get or set the power alarm threshold of R1 in link25."
			::= { link25OBP 9 }

		
--  1.3.6.1.4.1.47477.10.21.25.3.10
		-- 1.3.6.1.4.1.47477.10.21.25.3.10
		link25_R2AlarmPower OBJECT-TYPE
			SYNTAX DisplayString
			MAX-ACCESS read-write
			STATUS current
			DESCRIPTION
				"get or set the power alarm threshold of R2 in link25."
			::= { link25OBP 10 }


--  1.3.6.1.4.1.47477.10.21.25.3.29
		-- 1.3.6.1.4.1.47477.10.21.25.3.29
		link25_R3AlarmPower OBJECT-TYPE
			SYNTAX DisplayString
			MAX-ACCESS read-write
			STATUS current
			DESCRIPTION
				"get or set the power alarm threshold of R3 in link25."
			::= { link25OBP 29 }

		
--  1.3.6.1.4.1.47477.10.21.25.3.30
		-- 1.3.6.1.4.1.47477.10.21.25.3.30
		link25_R4AlarmPower OBJECT-TYPE
			SYNTAX DisplayString
			MAX-ACCESS read-write
			STATUS current
			DESCRIPTION
				"get or set the power alarm threshold of R4 in link25."
			::= { link25OBP 30 }

-- OBP4
--  1.3.6.1.4.1.47477.10.21.25.3.37
		-- 1.3.6.1.4.1.47477.10.21.25.3.37
		link25_1R1Power OBJECT-TYPE
			SYNTAX DisplayString
			MAX-ACCESS read-only
			STATUS current
			DESCRIPTION
				"get the power of 1R1 in link25."
			::= { link25OBP 37 }
			
--  1.3.6.1.4.1.47477.10.21.25.3.38
		-- 1.3.6.1.4.1.47477.10.21.25.3.38
		link25_1R2Power OBJECT-TYPE
			SYNTAX DisplayString
			MAX-ACCESS read-only
			STATUS current
			DESCRIPTION
				"get the power of 1R2 in link25."
			::= { link25OBP 38 }

--  1.3.6.1.4.1.47477.10.21.25.3.39
		-- 1.3.6.1.4.1.47477.10.21.25.3.39
		link25_1R3Power OBJECT-TYPE
			SYNTAX DisplayString
			MAX-ACCESS read-only
			STATUS current
			DESCRIPTION
				"get the power of 1R3 in link25."
			::= { link25OBP 39 }
			
--  1.3.6.1.4.1.47477.10.21.25.3.40
		-- 1.3.6.1.4.1.47477.10.21.25.3.40
		link25_1R4Power OBJECT-TYPE
			SYNTAX DisplayString
			MAX-ACCESS read-only
			STATUS current
			DESCRIPTION
				"get the power of 1R4 in link25."
			::= { link25OBP 40 }

--  1.3.6.1.4.1.47477.10.21.25.3.41
		-- 1.3.6.1.4.1.47477.10.21.25.3.41
		link25_2R1Power OBJECT-TYPE
			SYNTAX DisplayString
			MAX-ACCESS read-only
			STATUS current
			DESCRIPTION
				"get the power of 2R1 in link25."
			::= { link25OBP 41 }
			
--  1.3.6.1.4.1.47477.10.21.25.3.42
		-- 1.3.6.1.4.1.47477.10.21.25.3.42
		link25_2R2Power OBJECT-TYPE
			SYNTAX DisplayString
			MAX-ACCESS read-only
			STATUS current
			DESCRIPTION
				"get the power of 2R2 in link25."
			::= { link25OBP 42 }

--  1.3.6.1.4.1.47477.10.21.25.3.41
		-- 1.3.6.1.4.1.47477.10.21.25.3.43
		link25_2R3Power OBJECT-TYPE
			SYNTAX DisplayString
			MAX-ACCESS read-only
			STATUS current
			DESCRIPTION
				"get the power of 2R3 in link25."
			::= { link25OBP 43 }
			
--  1.3.6.1.4.1.47477.10.21.25.3.42
		-- 1.3.6.1.4.1.47477.10.21.25.3.44
		link25_2R4Power OBJECT-TYPE
			SYNTAX DisplayString
			MAX-ACCESS read-only
			STATUS current
			DESCRIPTION
				"get the power of 2R4 in link25."
			::= { link25OBP 44 }
			
--  1.3.6.1.4.1.47477.10.21.25.3.49
		-- 1.3.6.1.4.1.47477.10.21.25.3.49
		link25_1R1Wave OBJECT-TYPE
			SYNTAX INTEGER
				{
				w850nm(0),
				na(2)
				}
			MAX-ACCESS read-only
			STATUS current
			DESCRIPTION
				"get the wave length of 1R1 in link25."
			::= { link25OBP 49 }
		
--  1.3.6.1.4.1.47477.10.21.25.3.60
		-- 1.3.6.1.4.1.47477.10.21.25.3.60
		link25_1R2Wave OBJECT-TYPE
			SYNTAX INTEGER
				{
				w850nm(0),
				na(2)
				}
			MAX-ACCESS read-only
			STATUS current
			DESCRIPTION
				"get the wave length of 1R2 in link25."
			::= { link25OBP 60 }

--  1.3.6.1.4.1.47477.10.21.25.3.61
		-- 1.3.6.1.4.1.47477.10.21.25.3.61
		link25_1R3Wave OBJECT-TYPE
			SYNTAX INTEGER
				{
				w850nm(0),
				na(2)
				}
			MAX-ACCESS read-only
			STATUS current
			DESCRIPTION
				"get the wave length of 1R3 in link25."
			::= { link25OBP 61 }

		
--  1.3.6.1.4.1.47477.10.21.25.3.62
		-- 1.3.6.1.4.1.47477.10.21.25.3.62
		link25_1R4Wave OBJECT-TYPE
			SYNTAX INTEGER
				{
				w850nm(0),
				na(2)
				}
			MAX-ACCESS read-only
			STATUS current
			DESCRIPTION
				"get the wave length of 1R4 in link25."
			::= { link25OBP 62 }
	
--  1.3.6.1.4.1.47477.10.21.25.3.63
		-- 1.3.6.1.4.1.47477.10.21.25.3.63
		link25_2R1Wave OBJECT-TYPE
			SYNTAX INTEGER
				{
				w850nm(0),
				na(2)
				}
			MAX-ACCESS read-only
			STATUS current
			DESCRIPTION
				"get the wave length of 2R1 in link25."
			::= { link25OBP 63 }

		
--  1.3.6.1.4.1.47477.10.21.25.3.64
		-- 1.3.6.1.4.1.47477.10.21.25.3.64
		link25_2R2Wave OBJECT-TYPE
			SYNTAX INTEGER
				{
				w850nm(0),
				na(2)
				}
			MAX-ACCESS read-only
			STATUS current
			DESCRIPTION
				"get the wave length of 2R2 in link25."
			::= { link25OBP 64 }	
	
--  1.3.6.1.4.1.47477.10.21.25.3.65
		-- 1.3.6.1.4.1.47477.10.21.25.3.65
		link25_2R3Wave OBJECT-TYPE
			SYNTAX INTEGER
				{
				w850nm(0),
				na(2)
				}
			MAX-ACCESS read-only
			STATUS current
			DESCRIPTION
				"get the wave length of 2R3 in link25."
			::= { link25OBP 65 }

		
--  1.3.6.1.4.1.47477.10.21.25.3.66
		-- 1.3.6.1.4.1.47477.10.21.25.3.66
		link25_2R4Wave OBJECT-TYPE
			SYNTAX INTEGER
				{
				w850nm(0),
				na(2)
				}
			MAX-ACCESS read-only
			STATUS current
			DESCRIPTION
				"get the wave length of 2R4 in link25."
			::= { link25OBP 66 }	
			
--  1.3.6.1.4.1.47477.10.21.25.3.31
		-- 1.3.6.1.4.1.47477.10.21.25.3.31
		link25_1R1AlarmPower OBJECT-TYPE
			SYNTAX DisplayString
			MAX-ACCESS read-write
			STATUS current
			DESCRIPTION
				"get or set the power alarm threshold of 1R1 in link25."
			::= { link25OBP 31 }
			
--  1.3.6.1.4.1.47477.10.21.25.3.32
		-- 1.3.6.1.4.1.47477.10.21.25.3.32
		link25_1R2AlarmPower OBJECT-TYPE
			SYNTAX DisplayString
			MAX-ACCESS read-write
			STATUS current
			DESCRIPTION
				"get or set the power alarm threshold of 1R2 in link25."
			::= { link25OBP 32 }

--  1.3.6.1.4.1.47477.10.21.25.3.33
		-- 1.3.6.1.4.1.47477.10.21.25.3.33
		link25_1R3AlarmPower OBJECT-TYPE
			SYNTAX DisplayString
			MAX-ACCESS read-write
			STATUS current
			DESCRIPTION
				"get or set the power alarm threshold of 1R3 in link25."
			::= { link25OBP 33 }
			
--  1.3.6.1.4.1.47477.10.21.25.3.34
		-- 1.3.6.1.4.1.47477.10.21.25.3.34
		link25_1R4AlarmPower OBJECT-TYPE
			SYNTAX DisplayString
			MAX-ACCESS read-write
			STATUS current
			DESCRIPTION
				"get or set the power alarm threshold of 1R4 in link25."
			::= { link25OBP 34 }

--  1.3.6.1.4.1.47477.10.21.25.3.45
		-- 1.3.6.1.4.1.47477.10.21.25.3.45
		link25_2R1AlarmPower OBJECT-TYPE
			SYNTAX DisplayString
			MAX-ACCESS read-write
			STATUS current
			DESCRIPTION
				"get or set the power alarm threshold of 2R1 in link25."
			::= { link25OBP 45 }
			
--  1.3.6.1.4.1.47477.10.21.25.3.46
		-- 1.3.6.1.4.1.47477.10.21.25.3.46
		link25_2R2AlarmPower OBJECT-TYPE
			SYNTAX DisplayString
			MAX-ACCESS read-write
			STATUS current
			DESCRIPTION
				"get or set the power alarm threshold of 2R2 in link25."
			::= { link25OBP 46 }

--  1.3.6.1.4.1.47477.10.21.25.3.47
		-- 1.3.6.1.4.1.47477.10.21.25.3.47
		link25_2R3AlarmPower OBJECT-TYPE
			SYNTAX DisplayString
			MAX-ACCESS read-write
			STATUS current
			DESCRIPTION
				"get or set the power alarm threshold of 2R3 in link25."
			::= { link25OBP 47 }
			
--  1.3.6.1.4.1.47477.10.21.25.3.48
		-- 1.3.6.1.4.1.47477.10.21.25.3.48
		link25_2R4AlarmPower OBJECT-TYPE
			SYNTAX DisplayString
			MAX-ACCESS read-write
			STATUS current
			DESCRIPTION
				"get or set the power alarm threshold of 2R4 in link25."
			::= { link25OBP 48 }
			
--  1.3.6.1.4.1.47477.10.21.25.3.11
		-- 1.3.6.1.4.1.47477.10.21.25.3.11
		link25_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link25OBP 11 }
			
--  1.3.6.1.4.1.47477.10.21.25.3.67
		-- 1.3.6.1.4.1.47477.10.21.25.3.67
		link25_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link25OBP 67 }
			
--  1.3.6.1.4.1.47477.10.21.25.3.68
		-- 1.3.6.1.4.1.47477.10.21.25.3.68
		link25_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link25OBP 68 }
			
--  1.3.6.1.4.1.47477.10.21.25.3.12
		-- 1.3.6.1.4.1.47477.10.21.25.3.12
		link25_ReturnDelay OBJECT-TYPE
			--SYNTAX Integer32
			SYNTAX Integer32
			MAX-ACCESS read-write
			STATUS current
			DESCRIPTION
				"get or set how long link25 takes to return to automatic mode."
			::= { link25OBP 12 }
			
--  1.3.6.1.4.1.47477.10.21.25.3.13
		-- 1.3.6.1.4.1.47477.10.21.25.3.13
		link25_BackMode OBJECT-TYPE
			SYNTAX INTEGER
				{
				autoNoBack(0),
				autoBack(1)
				}
			MAX-ACCESS read-write
			STATUS current
			DESCRIPTION
				"get or set the back mode of link25."
			::= { link25OBP 13 }

		
--  1.3.6.1.4.1.47477.10.21.25.3.14
		-- 1.3.6.1.4.1.47477.10.21.25.3.14
		link25_BackDelay OBJECT-TYPE
			SYNTAX Integer32
			MAX-ACCESS read-write
			STATUS current
			DESCRIPTION
				"get or set the back delay."
			::= { link25OBP 14 }

--  1.3.6.1.4.1.47477.10.21.25.3.15
		-- 1.3.6.1.4.1.47477.10.21.25.3.15
		link25_ActiveHeartSwitch OBJECT-TYPE
			SYNTAX INTEGER
				{
				off(0),
				on(1)
				}
			MAX-ACCESS read-write
			STATUS current
			DESCRIPTION
				"get or set the switch status of active heartbeat."
			::= { link25OBP 15 }

		
--  1.3.6.1.4.1.47477.10.21.25.3.16
		-- 1.3.6.1.4.1.47477.10.21.25.3.16
		link25_ActiveSendInterval OBJECT-TYPE
			SYNTAX Integer32
			MAX-ACCESS read-write
			STATUS current
			DESCRIPTION
				"get or set the send interval of active heartbeat."
			::= { link25OBP 16 }		

--  1.3.6.1.4.1.47477.10.21.25.3.17
		-- 1.3.6.1.4.1.47477.10.21.25.3.17
		link25_ActiveTimeOut OBJECT-TYPE
			SYNTAX Integer32
			MAX-ACCESS read-write
			STATUS current
			DESCRIPTION
				"get or set how long the active heartbeat send timeout."
			::= { link25OBP 17 }

--  1.3.6.1.4.1.47477.10.21.25.3.18
		-- 1.3.6.1.4.1.47477.10.21.25.3.18
		link25_ActiveLossBypass OBJECT-TYPE
			SYNTAX Integer32
			MAX-ACCESS read-write
			STATUS current
			DESCRIPTION
				"get or set the bypass for active heartbeat packet loss."
			::= { link25OBP 18 }

--  1.3.6.1.4.1.47477.10.21.25.3.19
		-- 1.3.6.1.4.1.47477.10.21.25.3.19
		link25_PingIpAddress OBJECT-TYPE
			SYNTAX IpAddress
			MAX-ACCESS read-write
			STATUS current
			DESCRIPTION
				"get or set the ping ip address of link25."
			::= { link25OBP 19 }

--  1.3.6.1.4.1.47477.10.21.25.3.20
		-- 1.3.6.1.4.1.47477.10.21.25.3.20
		link25_PassiveHeartSwitch OBJECT-TYPE
			SYNTAX INTEGER
				{
				off(0),
				on(1)
				}
			MAX-ACCESS read-write
			STATUS current
			DESCRIPTION
				"get or set the switch status of passive heartbeat."
			::= { link25OBP 20 }
	

--  1.3.6.1.4.1.47477.10.21.25.3.21
		-- 1.3.6.1.4.1.47477.10.21.25.3.21
		link25_PassiveTimeOut OBJECT-TYPE
			SYNTAX Integer32
			MAX-ACCESS read-write
			STATUS current
			DESCRIPTION
				"get or set how long the passive heartbeat send timeout."
			::= { link25OBP 21 }

--  1.3.6.1.4.1.47477.10.21.25.3.22
		-- 1.3.6.1.4.1.47477.10.21.25.3.22
		link25_PassiveLossBypass OBJECT-TYPE
			SYNTAX Integer32
			MAX-ACCESS read-write
			STATUS current
			DESCRIPTION
				"get or set the bypass for passive heartbeat packet loss."
			::= { link25OBP 22 }

--  1.3.6.1.4.1.47477.10.21.25.3.23
		-- 1.3.6.1.4.1.47477.10.21.25.3.23
		link25_SwitchProtect OBJECT-TYPE
			SYNTAX INTEGER
				{
				off(0),
				on(1)
				}
			MAX-ACCESS read-write
			STATUS current
			DESCRIPTION
				"get or set the switch protection status of link25."
			::= { link25OBP 23 }
			
--  1.3.6.1.4.1.47477.10.21.25.3.24
		-- 1.3.6.1.4.1.47477.10.21.25.3.24
		link25_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link25OBP 24 }		

--  1.3.6.1.4.1.47477.10.21.25.3.25
		-- 1.3.6.1.4.1.47477.10.21.25.3.25
		link25_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link25OBP 25 }	

--  1.3.6.1.4.1.47477.10.21.25.3.26
		-- 1.3.6.1.4.1.47477.10.21.25.3.26
		link25_PowerAlarmStatus OBJECT-TYPE
			SYNTAX INTEGER
				{
				off(0),
				alarm(1),
				normal(2),
				na(3)
				}
			MAX-ACCESS read-only
			STATUS current
			DESCRIPTION
				"get whether a power alarm is generated."
			::= { link25OBP 26 }	


-- 1.3.6.1.4.1.47477.10.21.25.3.50.1
	link25_WorkModeChange 	OBJECT-TYPE    
    SYNTAX INTEGER	{
				manualMode(0),
				autoMode(1)
		}
	MAX-ACCESS read-only
	STATUS current
    DESCRIPTION
        "The Link mode Changed."
    ::= {link25OBPTrap 1}

-- 1.3.6.1.4.1.47477.10.21.25.3.50.2
	link25_StateChange 	OBJECT-TYPE    
    SYNTAX INTEGER	{
				bypass(0),
				primary(1)
		}
	MAX-ACCESS read-only
	STATUS current
    DESCRIPTION
        "The Link State(Channel) Changed."
    ::= {link25OBPTrap 2}

-- 1.3.6.1.4.1.47477.10.21.25.3.50.3
	link25_R1WaveSet 	OBJECT-TYPE    
    SYNTAX INTEGER	{
				w1310nm(0),
				w1550nm(1)
		}
	MAX-ACCESS read-only
	STATUS current
    DESCRIPTION
        "Set The link25 R1 Wave."
    ::= {link25OBPTrap 3}

-- 1.3.6.1.4.1.47477.10.21.25.3.50.4
	link25_R2WaveSet 	OBJECT-TYPE    
    SYNTAX INTEGER	{
				w1310nm(0),
				w1550nm(1)
		}
	MAX-ACCESS read-only
	STATUS current
    DESCRIPTION
        "Set The link25 R2 Wave."
    ::= {link25OBPTrap 4}			

-- 1.3.6.1.4.1.47477.10.21.25.3.50.5
	link25_R3WaveSet 	OBJECT-TYPE    
    SYNTAX INTEGER	{
				w1310nm(0),
				w1550nm(1)
		}
	MAX-ACCESS read-only
	STATUS current
    DESCRIPTION
        "Set The link25 R3 Wave."
    ::= {link25OBPTrap 5}

-- 1.3.6.1.4.1.47477.10.21.25.3.50.6
	link25_R4WaveSet 	OBJECT-TYPE    
    SYNTAX INTEGER	{
				w1310nm(0),
				w1550nm(1)
		}
	MAX-ACCESS read-only
	STATUS current
    DESCRIPTION
        "Set The link25 R4 Wave."
    ::= {link25OBPTrap 6}	
	
-- 1.3.6.1.4.1.47477.10.21.25.3.50.7
	link25_R1AlarmSet 	OBJECT-TYPE    
    SYNTAX DisplayString
	MAX-ACCESS read-only
	STATUS current
    DESCRIPTION
        "Set The link25 R1 Alarm Threshold."
    ::= {link25OBPTrap 7}

-- 1.3.6.1.4.1.47477.10.21.25.3.50.8
	link25_R2AlarmSet 	OBJECT-TYPE    
    SYNTAX DisplayString
	MAX-ACCESS read-only
	STATUS current
    DESCRIPTION
        "Set The link25 R2 Alarm Threshold."
    ::= {link25OBPTrap 8}
	
-- 1.3.6.1.4.1.47477.10.21.25.3.50.9
	link25_R3AlarmSet 	OBJECT-TYPE    
    SYNTAX DisplayString
	MAX-ACCESS read-only
	STATUS current
    DESCRIPTION
        "Set The link25 R3 Alarm Threshold."
    ::= {link25OBPTrap 9}

-- 1.3.6.1.4.1.47477.10.21.25.3.50.10
	link25_R4AlarmSet 	OBJECT-TYPE    
    SYNTAX DisplayString
	MAX-ACCESS read-only
	STATUS current
    DESCRIPTION
        "Set The link25 R4 Alarm Threshold."
    ::= {link25OBPTrap 10}	
	
	
-- 1.3.6.1.4.1.47477.10.21.25.3.50.11
	link25_1R1AlarmSet 	OBJECT-TYPE    
    SYNTAX DisplayString
	MAX-ACCESS read-only
	STATUS current
    DESCRIPTION
        "Set The link25 1R1 Alarm Threshold."
    ::= {link25OBPTrap 11}

-- 1.3.6.1.4.1.47477.10.21.25.3.50.12
	link25_2R1AlarmSet 	OBJECT-TYPE    
    SYNTAX DisplayString
	MAX-ACCESS read-only
	STATUS current
    DESCRIPTION
        "Set The link25 2R1 Alarm Threshold."
    ::= {link25OBPTrap 12}
	
-- 1.3.6.1.4.1.47477.10.21.25.3.50.13
	link25_1R2AlarmSet 	OBJECT-TYPE    
    SYNTAX DisplayString
	MAX-ACCESS read-only
	STATUS current
    DESCRIPTION
        "Set The link25 1R2 Alarm Threshold."
    ::= {link25OBPTrap 13}

-- 1.3.6.1.4.1.47477.10.21.25.3.50.14
	link25_2R2AlarmSet 	OBJECT-TYPE    
    SYNTAX DisplayString
	MAX-ACCESS read-only
	STATUS current
    DESCRIPTION
        "Set The link25 2R2 Alarm Threshold."
    ::= {link25OBPTrap 14}
	
-- 1.3.6.1.4.1.47477.10.21.25.3.50.15
	link25_1R3AlarmSet 	OBJECT-TYPE    
    SYNTAX DisplayString
	MAX-ACCESS read-only
	STATUS current
    DESCRIPTION
        "Set The link25 1R3 Alarm Threshold."
    ::= {link25OBPTrap 15}

-- 1.3.6.1.4.1.47477.10.21.25.3.50.16
	link25_2R3AlarmSet 	OBJECT-TYPE    
    SYNTAX DisplayString
	MAX-ACCESS read-only
	STATUS current
    DESCRIPTION
        "Set The link25 2R3 Alarm Threshold."
    ::= {link25OBPTrap 16}
	
-- 1.3.6.1.4.1.47477.10.21.25.3.50.17
	link25_1R4AlarmSet 	OBJECT-TYPE    
    SYNTAX DisplayString
	MAX-ACCESS read-only
	STATUS current
    DESCRIPTION
        "Set The link25 1R4 Alarm Threshold."
    ::= {link25OBPTrap 17}

-- 1.3.6.1.4.1.47477.10.21.25.3.50.18
	link25_2R4AlarmSet 	OBJECT-TYPE    
    SYNTAX DisplayString
	MAX-ACCESS read-only
	STATUS current
    DESCRIPTION
        "Set The link25 2R4 Alarm Threshold."
    ::= {link25OBPTrap 18}
	
-- 1.3.6.1.4.1.47477.10.21.25.3.50.19
	link25_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link25 PowerAlarmBypass2 Changed."
    ::= {link25OBPTrap 19}
	
-- 1.3.6.1.4.1.47477.10.21.25.3.50.20
	link25_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link25 PowerAlarmBypass4 Changed."
    ::= {link25OBPTrap 20}	
	
-- 1.3.6.1.4.1.47477.10.21.25.3.50.21
	link25_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link25 PowerAlarmBypass8 Changed."
    ::= {link25OBPTrap 21}
	
-- 1.3.6.1.4.1.47477.10.21.25.3.50.22
	link25_powerAlarmR1 	OBJECT-TYPE    
    SYNTAX DisplayString
	MAX-ACCESS read-only
	STATUS current
    DESCRIPTION
        "Set The link25 R1 Power Status Alarm."
    ::= {link25OBPTrap 22}
	
-- 1.3.6.1.4.1.47477.10.21.25.3.50.23
	link25_powerAlarmR2 	OBJECT-TYPE    
    SYNTAX DisplayString
	MAX-ACCESS read-only
	STATUS current
    DESCRIPTION
        "Set The link25 R2 Power Status Alarm."
    ::= {link25OBPTrap 23}
	
-- 1.3.6.1.4.1.47477.10.21.25.3.50.24
	link25_powerAlarmR3 	OBJECT-TYPE    
    SYNTAX DisplayString
	MAX-ACCESS read-only
	STATUS current
    DESCRIPTION
        "Set The link25 R3 Power Status Alarm."
    ::= {link25OBPTrap 24}
	
-- 1.3.6.1.4.1.47477.10.21.25.3.50.25
	link25_powerAlarmR4 	OBJECT-TYPE    
    SYNTAX DisplayString
	MAX-ACCESS read-only
	STATUS current
    DESCRIPTION
        "Set The link25 R4 Power Status Alarm."
    ::= {link25OBPTrap 25}
	
	
-- 1.3.6.1.4.1.47477.10.21.25.3.50.26
	link25_powerAlarm1R1 	OBJECT-TYPE    
    SYNTAX DisplayString
	MAX-ACCESS read-only
	STATUS current
    DESCRIPTION
        "Set The link25 1R1 Power Status Alarm."
    ::= {link25OBPTrap 26}
	
-- 1.3.6.1.4.1.47477.10.21.25.3.50.27
	link25_powerAlarm2R1 	OBJECT-TYPE    
    SYNTAX DisplayString
	MAX-ACCESS read-only
	STATUS current
    DESCRIPTION
        "Set The link25 2R1 Power Status Alarm."
    ::= {link25OBPTrap 27}
	
-- 1.3.6.1.4.1.47477.10.21.25.3.50.28
	link25_powerAlarm1R2 	OBJECT-TYPE    
    SYNTAX DisplayString
	MAX-ACCESS read-only
	STATUS current
    DESCRIPTION
        "Set The link25 1R2 Power Status Alarm."
    ::= {link25OBPTrap 28}
	
-- 1.3.6.1.4.1.47477.10.21.25.3.50.29
	link25_powerAlarm2R2 	OBJECT-TYPE    
    SYNTAX DisplayString
	MAX-ACCESS read-only
	STATUS current
    DESCRIPTION
        "Set The link25 2R2 Power Status Alarm."
    ::= {link25OBPTrap 29}
	
-- 1.3.6.1.4.1.47477.10.21.25.3.50.30
	link25_powerAlarm1R3 	OBJECT-TYPE    
    SYNTAX DisplayString
	MAX-ACCESS read-only
	STATUS current
    DESCRIPTION
        "Set The link25 1R3 Power Status Alarm."
    ::= {link25OBPTrap 30}
	
-- 1.3.6.1.4.1.47477.10.21.25.3.50.31
	link25_powerAlarm2R3 	OBJECT-TYPE    
    SYNTAX DisplayString
	MAX-ACCESS read-only
	STATUS current
    DESCRIPTION
        "Set The link25 2R1 Power Status Alarm."
    ::= {link25OBPTrap 31}
	
-- 1.3.6.1.4.1.47477.10.21.25.3.50.32
	link25_powerAlarm1R4 	OBJECT-TYPE    
    SYNTAX DisplayString
	MAX-ACCESS read-only
	STATUS current
    DESCRIPTION
        "Set The link25 1R4 Power Status Alarm."
    ::= {link25OBPTrap 32}
	
-- 1.3.6.1.4.1.47477.10.21.25.3.50.33
	link25_powerAlarm2R4 	OBJECT-TYPE    
    SYNTAX DisplayString
	MAX-ACCESS read-only
	STATUS current
    DESCRIPTION
        "Set The link25 2R4 Power Status Alarm."
    ::= {link25OBPTrap 33}
	
--  1.3.6.1.4.1.47477.10.21.26.3.1
		-- 1.3.6.1.4.1.47477.10.21.26.3.1
		link26_State OBJECT-TYPE
			SYNTAX INTEGER
				{
				off(0),
				on(1)
				}
			MAX-ACCESS read-only
			STATUS current
			DESCRIPTION
				"get the information about whether link26 is working."
			::= { link26OBP 1 }

		
--  1.3.6.1.4.1.47477.10.21.26.3.2
		-- 1.3.6.1.4.1.47477.10.21.26.3.2
		link26_DeviceType OBJECT-TYPE
			SYNTAX DisplayString
			MAX-ACCESS read-only
			STATUS current
			DESCRIPTION
				"get the type of card in link26."
			::= { link26OBP 2 }

			
--  1.3.6.1.4.1.47477.10.21.26.3.3
		-- 1.3.6.1.4.1.47477.10.21.26.3.3
		link26_WorkMode OBJECT-TYPE
			SYNTAX INTEGER
				{
				manualMode(0),
				autoMode(1)
				}
			MAX-ACCESS read-write
			STATUS current
			DESCRIPTION
				"get or set link26's work mode."
			::= { link26OBP 3 }

		
--  1.3.6.1.4.1.47477.10.21.26.3.4
		-- 1.3.6.1.4.1.47477.10.21.26.3.4
		link26_Channel OBJECT-TYPE
			SYNTAX INTEGER
				{
				bypass(0),
				primary(1)
				}
			MAX-ACCESS read-write
			STATUS current
			DESCRIPTION
				"get or set the channel in which link26 works."
			::= { link26OBP 4 }


--  1.3.6.1.4.1.47477.10.21.26.3.5
		-- 1.3.6.1.4.1.47477.10.21.26.3.5
		link26_R1Power OBJECT-TYPE
			SYNTAX DisplayString
			MAX-ACCESS read-only
			STATUS current
			DESCRIPTION
				"get the power of R1 in link26."
			::= { link26OBP 5 }

		
--  1.3.6.1.4.1.47477.10.21.26.3.6
		-- 1.3.6.1.4.1.47477.10.21.26.3.6
		link26_R2Power OBJECT-TYPE
			SYNTAX DisplayString
			MAX-ACCESS read-only
			STATUS current
			DESCRIPTION
				"get the power of R2 in link26."
			::= { link26OBP 6 }
			
--  1.3.6.1.4.1.47477.10.21.26.3.35
		-- 1.3.6.1.4.1.47477.10.21.26.3.35
		link26_R3Power OBJECT-TYPE
			SYNTAX DisplayString
			MAX-ACCESS read-only
			STATUS current
			DESCRIPTION
				"get the power of R3 in link26."
			::= { link26OBP 35 }
			
--  1.3.6.1.4.1.47477.10.21.26.3.36
		-- 1.3.6.1.4.1.47477.10.21.26.3.36
		link26_R4Power OBJECT-TYPE
			SYNTAX DisplayString
			MAX-ACCESS read-only
			STATUS current
			DESCRIPTION
				"get the power of R4 in link26."
			::= { link26OBP 36 }		
		
--  1.3.6.1.4.1.47477.10.21.26.3.7
		-- 1.3.6.1.4.1.47477.10.21.26.3.7
		link26_R1Wave OBJECT-TYPE
			SYNTAX INTEGER
				{
				w1310nm(0),
				w1550nm(1),
				na(2)
				}
			MAX-ACCESS read-write
			STATUS current
			DESCRIPTION
				"get or set the wave length of R1 in link26."
			::= { link26OBP 7 }

		
--  1.3.6.1.4.1.47477.10.21.26.3.8
		-- 1.3.6.1.4.1.47477.10.21.26.3.8
		link26_R2Wave OBJECT-TYPE
			SYNTAX INTEGER
				{
				w1310nm(0),
				w1550nm(1),
				na(2)
				}
			MAX-ACCESS read-write
			STATUS current
			DESCRIPTION
				"get or set the wave length of R2 in link26."
			::= { link26OBP 8 }


--  1.3.6.1.4.1.47477.10.21.26.3.27
		-- 1.3.6.1.4.1.47477.10.21.26.3.27
		link26_R3Wave OBJECT-TYPE
			SYNTAX INTEGER
				{
				w1310nm(0),
				w1550nm(1),
				na(2)
				}
			MAX-ACCESS read-write
			STATUS current
			DESCRIPTION
				"get or set the wave length of R3 in link26."
			::= { link26OBP 27 }

		
--  1.3.6.1.4.1.47477.10.21.26.3.28
		-- 1.3.6.1.4.1.47477.10.21.26.3.28
		link26_R4Wave OBJECT-TYPE
			SYNTAX INTEGER
				{
				w1310nm(0),
				w1550nm(1),
				na(2)
				}
			MAX-ACCESS read-write
			STATUS current
			DESCRIPTION
				"get or set the wave length of R4 in link26."
			::= { link26OBP 28 }
			
--  1.3.6.1.4.1.47477.10.21.26.3.9
		-- 1.3.6.1.4.1.47477.10.21.26.3.9
		link26_R1AlarmPower OBJECT-TYPE
			SYNTAX DisplayString
			MAX-ACCESS read-write
			STATUS current
			DESCRIPTION
				"get or set the power alarm threshold of R1 in link26."
			::= { link26OBP 9 }

		
--  1.3.6.1.4.1.47477.10.21.26.3.10
		-- 1.3.6.1.4.1.47477.10.21.26.3.10
		link26_R2AlarmPower OBJECT-TYPE
			SYNTAX DisplayString
			MAX-ACCESS read-write
			STATUS current
			DESCRIPTION
				"get or set the power alarm threshold of R2 in link26."
			::= { link26OBP 10 }


--  1.3.6.1.4.1.47477.10.21.26.3.29
		-- 1.3.6.1.4.1.47477.10.21.26.3.29
		link26_R3AlarmPower OBJECT-TYPE
			SYNTAX DisplayString
			MAX-ACCESS read-write
			STATUS current
			DESCRIPTION
				"get or set the power alarm threshold of R3 in link26."
			::= { link26OBP 29 }

		
--  1.3.6.1.4.1.47477.10.21.26.3.30
		-- 1.3.6.1.4.1.47477.10.21.26.3.30
		link26_R4AlarmPower OBJECT-TYPE
			SYNTAX DisplayString
			MAX-ACCESS read-write
			STATUS current
			DESCRIPTION
				"get or set the power alarm threshold of R4 in link26."
			::= { link26OBP 30 }

-- OBP4
--  1.3.6.1.4.1.47477.10.21.26.3.37
		-- 1.3.6.1.4.1.47477.10.21.26.3.37
		link26_1R1Power OBJECT-TYPE
			SYNTAX DisplayString
			MAX-ACCESS read-only
			STATUS current
			DESCRIPTION
				"get the power of 1R1 in link26."
			::= { link26OBP 37 }
			
--  1.3.6.1.4.1.47477.10.21.26.3.38
		-- 1.3.6.1.4.1.47477.10.21.26.3.38
		link26_1R2Power OBJECT-TYPE
			SYNTAX DisplayString
			MAX-ACCESS read-only
			STATUS current
			DESCRIPTION
				"get the power of 1R2 in link26."
			::= { link26OBP 38 }

--  1.3.6.1.4.1.47477.10.21.26.3.39
		-- 1.3.6.1.4.1.47477.10.21.26.3.39
		link26_1R3Power OBJECT-TYPE
			SYNTAX DisplayString
			MAX-ACCESS read-only
			STATUS current
			DESCRIPTION
				"get the power of 1R3 in link26."
			::= { link26OBP 39 }
			
--  1.3.6.1.4.1.47477.10.21.26.3.40
		-- 1.3.6.1.4.1.47477.10.21.26.3.40
		link26_1R4Power OBJECT-TYPE
			SYNTAX DisplayString
			MAX-ACCESS read-only
			STATUS current
			DESCRIPTION
				"get the power of 1R4 in link26."
			::= { link26OBP 40 }

--  1.3.6.1.4.1.47477.10.21.26.3.41
		-- 1.3.6.1.4.1.47477.10.21.26.3.41
		link26_2R1Power OBJECT-TYPE
			SYNTAX DisplayString
			MAX-ACCESS read-only
			STATUS current
			DESCRIPTION
				"get the power of 2R1 in link26."
			::= { link26OBP 41 }
			
--  1.3.6.1.4.1.47477.10.21.26.3.42
		-- 1.3.6.1.4.1.47477.10.21.26.3.42
		link26_2R2Power OBJECT-TYPE
			SYNTAX DisplayString
			MAX-ACCESS read-only
			STATUS current
			DESCRIPTION
				"get the power of 2R2 in link26."
			::= { link26OBP 42 }

--  1.3.6.1.4.1.47477.10.21.26.3.41
		-- 1.3.6.1.4.1.47477.10.21.26.3.43
		link26_2R3Power OBJECT-TYPE
			SYNTAX DisplayString
			MAX-ACCESS read-only
			STATUS current
			DESCRIPTION
				"get the power of 2R3 in link26."
			::= { link26OBP 43 }
			
--  1.3.6.1.4.1.47477.10.21.26.3.42
		-- 1.3.6.1.4.1.47477.10.21.26.3.44
		link26_2R4Power OBJECT-TYPE
			SYNTAX DisplayString
			MAX-ACCESS read-only
			STATUS current
			DESCRIPTION
				"get the power of 2R4 in link26."
			::= { link26OBP 44 }
			
--  1.3.6.1.4.1.47477.10.21.26.3.49
		-- 1.3.6.1.4.1.47477.10.21.26.3.49
		link26_1R1Wave OBJECT-TYPE
			SYNTAX INTEGER
				{
				w850nm(0),
				na(2)
				}
			MAX-ACCESS read-only
			STATUS current
			DESCRIPTION
				"get the wave length of 1R1 in link26."
			::= { link26OBP 49 }
		
--  1.3.6.1.4.1.47477.10.21.26.3.60
		-- 1.3.6.1.4.1.47477.10.21.26.3.60
		link26_1R2Wave OBJECT-TYPE
			SYNTAX INTEGER
				{
				w850nm(0),
				na(2)
				}
			MAX-ACCESS read-only
			STATUS current
			DESCRIPTION
				"get the wave length of 1R2 in link26."
			::= { link26OBP 60 }

--  1.3.6.1.4.1.47477.10.21.26.3.61
		-- 1.3.6.1.4.1.47477.10.21.26.3.61
		link26_1R3Wave OBJECT-TYPE
			SYNTAX INTEGER
				{
				w850nm(0),
				na(2)
				}
			MAX-ACCESS read-only
			STATUS current
			DESCRIPTION
				"get the wave length of 1R3 in link26."
			::= { link26OBP 61 }

		
--  1.3.6.1.4.1.47477.10.21.26.3.62
		-- 1.3.6.1.4.1.47477.10.21.26.3.62
		link26_1R4Wave OBJECT-TYPE
			SYNTAX INTEGER
				{
				w850nm(0),
				na(2)
				}
			MAX-ACCESS read-only
			STATUS current
			DESCRIPTION
				"get the wave length of 1R4 in link26."
			::= { link26OBP 62 }
	
--  1.3.6.1.4.1.47477.10.21.26.3.63
		-- 1.3.6.1.4.1.47477.10.21.26.3.63
		link26_2R1Wave OBJECT-TYPE
			SYNTAX INTEGER
				{
				w850nm(0),
				na(2)
				}
			MAX-ACCESS read-only
			STATUS current
			DESCRIPTION
				"get the wave length of 2R1 in link26."
			::= { link26OBP 63 }

		
--  1.3.6.1.4.1.47477.10.21.26.3.64
		-- 1.3.6.1.4.1.47477.10.21.26.3.64
		link26_2R2Wave OBJECT-TYPE
			SYNTAX INTEGER
				{
				w850nm(0),
				na(2)
				}
			MAX-ACCESS read-only
			STATUS current
			DESCRIPTION
				"get the wave length of 2R2 in link26."
			::= { link26OBP 64 }	
	
--  1.3.6.1.4.1.47477.10.21.26.3.65
		-- 1.3.6.1.4.1.47477.10.21.26.3.65
		link26_2R3Wave OBJECT-TYPE
			SYNTAX INTEGER
				{
				w850nm(0),
				na(2)
				}
			MAX-ACCESS read-only
			STATUS current
			DESCRIPTION
				"get the wave length of 2R3 in link26."
			::= { link26OBP 65 }

		
--  1.3.6.1.4.1.47477.10.21.26.3.66
		-- 1.3.6.1.4.1.47477.10.21.26.3.66
		link26_2R4Wave OBJECT-TYPE
			SYNTAX INTEGER
				{
				w850nm(0),
				na(2)
				}
			MAX-ACCESS read-only
			STATUS current
			DESCRIPTION
				"get the wave length of 2R4 in link26."
			::= { link26OBP 66 }	
			
--  1.3.6.1.4.1.47477.10.21.26.3.31
		-- 1.3.6.1.4.1.47477.10.21.26.3.31
		link26_1R1AlarmPower OBJECT-TYPE
			SYNTAX DisplayString
			MAX-ACCESS read-write
			STATUS current
			DESCRIPTION
				"get or set the power alarm threshold of 1R1 in link26."
			::= { link26OBP 31 }
			
--  1.3.6.1.4.1.47477.10.21.26.3.32
		-- 1.3.6.1.4.1.47477.10.21.26.3.32
		link26_1R2AlarmPower OBJECT-TYPE
			SYNTAX DisplayString
			MAX-ACCESS read-write
			STATUS current
			DESCRIPTION
				"get or set the power alarm threshold of 1R2 in link26."
			::= { link26OBP 32 }

--  1.3.6.1.4.1.47477.10.21.26.3.33
		-- 1.3.6.1.4.1.47477.10.21.26.3.33
		link26_1R3AlarmPower OBJECT-TYPE
			SYNTAX DisplayString
			MAX-ACCESS read-write
			STATUS current
			DESCRIPTION
				"get or set the power alarm threshold of 1R3 in link26."
			::= { link26OBP 33 }
			
--  1.3.6.1.4.1.47477.10.21.26.3.34
		-- 1.3.6.1.4.1.47477.10.21.26.3.34
		link26_1R4AlarmPower OBJECT-TYPE
			SYNTAX DisplayString
			MAX-ACCESS read-write
			STATUS current
			DESCRIPTION
				"get or set the power alarm threshold of 1R4 in link26."
			::= { link26OBP 34 }

--  1.3.6.1.4.1.47477.10.21.26.3.45
		-- 1.3.6.1.4.1.47477.10.21.26.3.45
		link26_2R1AlarmPower OBJECT-TYPE
			SYNTAX DisplayString
			MAX-ACCESS read-write
			STATUS current
			DESCRIPTION
				"get or set the power alarm threshold of 2R1 in link26."
			::= { link26OBP 45 }
			
--  1.3.6.1.4.1.47477.10.21.26.3.46
		-- 1.3.6.1.4.1.47477.10.21.26.3.46
		link26_2R2AlarmPower OBJECT-TYPE
			SYNTAX DisplayString
			MAX-ACCESS read-write
			STATUS current
			DESCRIPTION
				"get or set the power alarm threshold of 2R2 in link26."
			::= { link26OBP 46 }

--  1.3.6.1.4.1.47477.10.21.26.3.47
		-- 1.3.6.1.4.1.47477.10.21.26.3.47
		link26_2R3AlarmPower OBJECT-TYPE
			SYNTAX DisplayString
			MAX-ACCESS read-write
			STATUS current
			DESCRIPTION
				"get or set the power alarm threshold of 2R3 in link26."
			::= { link26OBP 47 }
			
--  1.3.6.1.4.1.47477.10.21.26.3.48
		-- 1.3.6.1.4.1.47477.10.21.26.3.48
		link26_2R4AlarmPower OBJECT-TYPE
			SYNTAX DisplayString
			MAX-ACCESS read-write
			STATUS current
			DESCRIPTION
				"get or set the power alarm threshold of 2R4 in link26."
			::= { link26OBP 48 }
			
--  1.3.6.1.4.1.47477.10.21.26.3.11
		-- 1.3.6.1.4.1.47477.10.21.26.3.11
		link26_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link26OBP 11 }
			
--  1.3.6.1.4.1.47477.10.21.26.3.67
		-- 1.3.6.1.4.1.47477.10.21.26.3.67
		link26_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link26OBP 67 }
			
--  1.3.6.1.4.1.47477.10.21.26.3.68
		-- 1.3.6.1.4.1.47477.10.21.26.3.68
		link26_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link26OBP 68 }
			
--  1.3.6.1.4.1.47477.10.21.26.3.12
		-- 1.3.6.1.4.1.47477.10.21.26.3.12
		link26_ReturnDelay OBJECT-TYPE
			--SYNTAX Integer32
			SYNTAX Integer32
			MAX-ACCESS read-write
			STATUS current
			DESCRIPTION
				"get or set how long link26 takes to return to automatic mode."
			::= { link26OBP 12 }
			
--  1.3.6.1.4.1.47477.10.21.26.3.13
		-- 1.3.6.1.4.1.47477.10.21.26.3.13
		link26_BackMode OBJECT-TYPE
			SYNTAX INTEGER
				{
				autoNoBack(0),
				autoBack(1)
				}
			MAX-ACCESS read-write
			STATUS current
			DESCRIPTION
				"get or set the back mode of link26."
			::= { link26OBP 13 }

		
--  1.3.6.1.4.1.47477.10.21.26.3.14
		-- 1.3.6.1.4.1.47477.10.21.26.3.14
		link26_BackDelay OBJECT-TYPE
			SYNTAX Integer32
			MAX-ACCESS read-write
			STATUS current
			DESCRIPTION
				"get or set the back delay."
			::= { link26OBP 14 }

--  1.3.6.1.4.1.47477.10.21.26.3.15
		-- 1.3.6.1.4.1.47477.10.21.26.3.15
		link26_ActiveHeartSwitch OBJECT-TYPE
			SYNTAX INTEGER
				{
				off(0),
				on(1)
				}
			MAX-ACCESS read-write
			STATUS current
			DESCRIPTION
				"get or set the switch status of active heartbeat."
			::= { link26OBP 15 }

		
--  1.3.6.1.4.1.47477.10.21.26.3.16
		-- 1.3.6.1.4.1.47477.10.21.26.3.16
		link26_ActiveSendInterval OBJECT-TYPE
			SYNTAX Integer32
			MAX-ACCESS read-write
			STATUS current
			DESCRIPTION
				"get or set the send interval of active heartbeat."
			::= { link26OBP 16 }		

--  1.3.6.1.4.1.47477.10.21.26.3.17
		-- 1.3.6.1.4.1.47477.10.21.26.3.17
		link26_ActiveTimeOut OBJECT-TYPE
			SYNTAX Integer32
			MAX-ACCESS read-write
			STATUS current
			DESCRIPTION
				"get or set how long the active heartbeat send timeout."
			::= { link26OBP 17 }

--  1.3.6.1.4.1.47477.10.21.26.3.18
		-- 1.3.6.1.4.1.47477.10.21.26.3.18
		link26_ActiveLossBypass OBJECT-TYPE
			SYNTAX Integer32
			MAX-ACCESS read-write
			STATUS current
			DESCRIPTION
				"get or set the bypass for active heartbeat packet loss."
			::= { link26OBP 18 }

--  1.3.6.1.4.1.47477.10.21.26.3.19
		-- 1.3.6.1.4.1.47477.10.21.26.3.19
		link26_PingIpAddress OBJECT-TYPE
			SYNTAX IpAddress
			MAX-ACCESS read-write
			STATUS current
			DESCRIPTION
				"get or set the ping ip address of link26."
			::= { link26OBP 19 }

--  1.3.6.1.4.1.47477.10.21.26.3.20
		-- 1.3.6.1.4.1.47477.10.21.26.3.20
		link26_PassiveHeartSwitch OBJECT-TYPE
			SYNTAX INTEGER
				{
				off(0),
				on(1)
				}
			MAX-ACCESS read-write
			STATUS current
			DESCRIPTION
				"get or set the switch status of passive heartbeat."
			::= { link26OBP 20 }
	

--  1.3.6.1.4.1.47477.10.21.26.3.21
		-- 1.3.6.1.4.1.47477.10.21.26.3.21
		link26_PassiveTimeOut OBJECT-TYPE
			SYNTAX Integer32
			MAX-ACCESS read-write
			STATUS current
			DESCRIPTION
				"get or set how long the passive heartbeat send timeout."
			::= { link26OBP 21 }

--  1.3.6.1.4.1.47477.10.21.26.3.22
		-- 1.3.6.1.4.1.47477.10.21.26.3.22
		link26_PassiveLossBypass OBJECT-TYPE
			SYNTAX Integer32
			MAX-ACCESS read-write
			STATUS current
			DESCRIPTION
				"get or set the bypass for passive heartbeat packet loss."
			::= { link26OBP 22 }

--  1.3.6.1.4.1.47477.10.21.26.3.23
		-- 1.3.6.1.4.1.47477.10.21.26.3.23
		link26_SwitchProtect OBJECT-TYPE
			SYNTAX INTEGER
				{
				off(0),
				on(1)
				}
			MAX-ACCESS read-write
			STATUS current
			DESCRIPTION
				"get or set the switch protection status of link26."
			::= { link26OBP 23 }
			
--  1.3.6.1.4.1.47477.10.21.26.3.24
		-- 1.3.6.1.4.1.47477.10.21.26.3.24
		link26_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link26OBP 24 }		

--  1.3.6.1.4.1.47477.10.21.26.3.25
		-- 1.3.6.1.4.1.47477.10.21.26.3.25
		link26_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link26OBP 25 }	

--  1.3.6.1.4.1.47477.10.21.26.3.26
		-- 1.3.6.1.4.1.47477.10.21.26.3.26
		link26_PowerAlarmStatus OBJECT-TYPE
			SYNTAX INTEGER
				{
				off(0),
				alarm(1),
				normal(2),
				na(3)
				}
			MAX-ACCESS read-only
			STATUS current
			DESCRIPTION
				"get whether a power alarm is generated."
			::= { link26OBP 26 }	


-- 1.3.6.1.4.1.47477.10.21.26.3.50.1
	link26_WorkModeChange 	OBJECT-TYPE    
    SYNTAX INTEGER	{
				manualMode(0),
				autoMode(1)
		}
	MAX-ACCESS read-only
	STATUS current
    DESCRIPTION
        "The Link mode Changed."
    ::= {link26OBPTrap 1}

-- 1.3.6.1.4.1.47477.10.21.26.3.50.2
	link26_StateChange 	OBJECT-TYPE    
    SYNTAX INTEGER	{
				bypass(0),
				primary(1)
		}
	MAX-ACCESS read-only
	STATUS current
    DESCRIPTION
        "The Link State(Channel) Changed."
    ::= {link26OBPTrap 2}

-- 1.3.6.1.4.1.47477.10.21.26.3.50.3
	link26_R1WaveSet 	OBJECT-TYPE    
    SYNTAX INTEGER	{
				w1310nm(0),
				w1550nm(1)
		}
	MAX-ACCESS read-only
	STATUS current
    DESCRIPTION
        "Set The link26 R1 Wave."
    ::= {link26OBPTrap 3}

-- 1.3.6.1.4.1.47477.10.21.26.3.50.4
	link26_R2WaveSet 	OBJECT-TYPE    
    SYNTAX INTEGER	{
				w1310nm(0),
				w1550nm(1)
		}
	MAX-ACCESS read-only
	STATUS current
    DESCRIPTION
        "Set The link26 R2 Wave."
    ::= {link26OBPTrap 4}			

-- 1.3.6.1.4.1.47477.10.21.26.3.50.5
	link26_R3WaveSet 	OBJECT-TYPE    
    SYNTAX INTEGER	{
				w1310nm(0),
				w1550nm(1)
		}
	MAX-ACCESS read-only
	STATUS current
    DESCRIPTION
        "Set The link26 R3 Wave."
    ::= {link26OBPTrap 5}

-- 1.3.6.1.4.1.47477.10.21.26.3.50.6
	link26_R4WaveSet 	OBJECT-TYPE    
    SYNTAX INTEGER	{
				w1310nm(0),
				w1550nm(1)
		}
	MAX-ACCESS read-only
	STATUS current
    DESCRIPTION
        "Set The link26 R4 Wave."
    ::= {link26OBPTrap 6}	
	
-- 1.3.6.1.4.1.47477.10.21.26.3.50.7
	link26_R1AlarmSet 	OBJECT-TYPE    
    SYNTAX DisplayString
	MAX-ACCESS read-only
	STATUS current
    DESCRIPTION
        "Set The link26 R1 Alarm Threshold."
    ::= {link26OBPTrap 7}

-- 1.3.6.1.4.1.47477.10.21.26.3.50.8
	link26_R2AlarmSet 	OBJECT-TYPE    
    SYNTAX DisplayString
	MAX-ACCESS read-only
	STATUS current
    DESCRIPTION
        "Set The link26 R2 Alarm Threshold."
    ::= {link26OBPTrap 8}
	
-- 1.3.6.1.4.1.47477.10.21.26.3.50.9
	link26_R3AlarmSet 	OBJECT-TYPE    
    SYNTAX DisplayString
	MAX-ACCESS read-only
	STATUS current
    DESCRIPTION
        "Set The link26 R3 Alarm Threshold."
    ::= {link26OBPTrap 9}

-- 1.3.6.1.4.1.47477.10.21.26.3.50.10
	link26_R4AlarmSet 	OBJECT-TYPE    
    SYNTAX DisplayString
	MAX-ACCESS read-only
	STATUS current
    DESCRIPTION
        "Set The link26 R4 Alarm Threshold."
    ::= {link26OBPTrap 10}	
	
	
-- 1.3.6.1.4.1.47477.10.21.26.3.50.11
	link26_1R1AlarmSet 	OBJECT-TYPE    
    SYNTAX DisplayString
	MAX-ACCESS read-only
	STATUS current
    DESCRIPTION
        "Set The link26 1R1 Alarm Threshold."
    ::= {link26OBPTrap 11}

-- 1.3.6.1.4.1.47477.10.21.26.3.50.12
	link26_2R1AlarmSet 	OBJECT-TYPE    
    SYNTAX DisplayString
	MAX-ACCESS read-only
	STATUS current
    DESCRIPTION
        "Set The link26 2R1 Alarm Threshold."
    ::= {link26OBPTrap 12}
	
-- 1.3.6.1.4.1.47477.10.21.26.3.50.13
	link26_1R2AlarmSet 	OBJECT-TYPE    
    SYNTAX DisplayString
	MAX-ACCESS read-only
	STATUS current
    DESCRIPTION
        "Set The link26 1R2 Alarm Threshold."
    ::= {link26OBPTrap 13}

-- 1.3.6.1.4.1.47477.10.21.26.3.50.14
	link26_2R2AlarmSet 	OBJECT-TYPE    
    SYNTAX DisplayString
	MAX-ACCESS read-only
	STATUS current
    DESCRIPTION
        "Set The link26 2R2 Alarm Threshold."
    ::= {link26OBPTrap 14}
	
-- 1.3.6.1.4.1.47477.10.21.26.3.50.15
	link26_1R3AlarmSet 	OBJECT-TYPE    
    SYNTAX DisplayString
	MAX-ACCESS read-only
	STATUS current
    DESCRIPTION
        "Set The link26 1R3 Alarm Threshold."
    ::= {link26OBPTrap 15}

-- 1.3.6.1.4.1.47477.10.21.26.3.50.16
	link26_2R3AlarmSet 	OBJECT-TYPE    
    SYNTAX DisplayString
	MAX-ACCESS read-only
	STATUS current
    DESCRIPTION
        "Set The link26 2R3 Alarm Threshold."
    ::= {link26OBPTrap 16}
	
-- 1.3.6.1.4.1.47477.10.21.26.3.50.17
	link26_1R4AlarmSet 	OBJECT-TYPE    
    SYNTAX DisplayString
	MAX-ACCESS read-only
	STATUS current
    DESCRIPTION
        "Set The link26 1R4 Alarm Threshold."
    ::= {link26OBPTrap 17}

-- 1.3.6.1.4.1.47477.10.21.26.3.50.18
	link26_2R4AlarmSet 	OBJECT-TYPE    
    SYNTAX DisplayString
	MAX-ACCESS read-only
	STATUS current
    DESCRIPTION
        "Set The link26 2R4 Alarm Threshold."
    ::= {link26OBPTrap 18}
	
-- 1.3.6.1.4.1.47477.10.21.26.3.50.19
	link26_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link26 PowerAlarmBypass2 Changed."
    ::= {link26OBPTrap 19}
	
-- 1.3.6.1.4.1.47477.10.21.26.3.50.20
	link26_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link26 PowerAlarmBypass4 Changed."
    ::= {link26OBPTrap 20}	
	
-- 1.3.6.1.4.1.47477.10.21.26.3.50.21
	link26_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link26 PowerAlarmBypass8 Changed."
    ::= {link26OBPTrap 21}
	
-- 1.3.6.1.4.1.47477.10.21.26.3.50.22
	link26_powerAlarmR1 	OBJECT-TYPE    
    SYNTAX DisplayString
	MAX-ACCESS read-only
	STATUS current
    DESCRIPTION
        "Set The link26 R1 Power Status Alarm."
    ::= {link26OBPTrap 22}
	
-- 1.3.6.1.4.1.47477.10.21.26.3.50.23
	link26_powerAlarmR2 	OBJECT-TYPE    
    SYNTAX DisplayString
	MAX-ACCESS read-only
	STATUS current
    DESCRIPTION
        "Set The link26 R2 Power Status Alarm."
    ::= {link26OBPTrap 23}
	
-- 1.3.6.1.4.1.47477.10.21.26.3.50.24
	link26_powerAlarmR3 	OBJECT-TYPE    
    SYNTAX DisplayString
	MAX-ACCESS read-only
	STATUS current
    DESCRIPTION
        "Set The link26 R3 Power Status Alarm."
    ::= {link26OBPTrap 24}
	
-- 1.3.6.1.4.1.47477.10.21.26.3.50.25
	link26_powerAlarmR4 	OBJECT-TYPE    
    SYNTAX DisplayString
	MAX-ACCESS read-only
	STATUS current
    DESCRIPTION
        "Set The link26 R4 Power Status Alarm."
    ::= {link26OBPTrap 25}
	
	
-- 1.3.6.1.4.1.47477.10.21.26.3.50.26
	link26_powerAlarm1R1 	OBJECT-TYPE    
    SYNTAX DisplayString
	MAX-ACCESS read-only
	STATUS current
    DESCRIPTION
        "Set The link26 1R1 Power Status Alarm."
    ::= {link26OBPTrap 26}
	
-- 1.3.6.1.4.1.47477.10.21.26.3.50.27
	link26_powerAlarm2R1 	OBJECT-TYPE    
    SYNTAX DisplayString
	MAX-ACCESS read-only
	STATUS current
    DESCRIPTION
        "Set The link26 2R1 Power Status Alarm."
    ::= {link26OBPTrap 27}
	
-- 1.3.6.1.4.1.47477.10.21.26.3.50.28
	link26_powerAlarm1R2 	OBJECT-TYPE    
    SYNTAX DisplayString
	MAX-ACCESS read-only
	STATUS current
    DESCRIPTION
        "Set The link26 1R2 Power Status Alarm."
    ::= {link26OBPTrap 28}
	
-- 1.3.6.1.4.1.47477.10.21.26.3.50.29
	link26_powerAlarm2R2 	OBJECT-TYPE    
    SYNTAX DisplayString
	MAX-ACCESS read-only
	STATUS current
    DESCRIPTION
        "Set The link26 2R2 Power Status Alarm."
    ::= {link26OBPTrap 29}
	
-- 1.3.6.1.4.1.47477.10.21.26.3.50.30
	link26_powerAlarm1R3 	OBJECT-TYPE    
    SYNTAX DisplayString
	MAX-ACCESS read-only
	STATUS current
    DESCRIPTION
        "Set The link26 1R3 Power Status Alarm."
    ::= {link26OBPTrap 30}
	
-- 1.3.6.1.4.1.47477.10.21.26.3.50.31
	link26_powerAlarm2R3 	OBJECT-TYPE    
    SYNTAX DisplayString
	MAX-ACCESS read-only
	STATUS current
    DESCRIPTION
        "Set The link26 2R1 Power Status Alarm."
    ::= {link26OBPTrap 31}
	
-- 1.3.6.1.4.1.47477.10.21.26.3.50.32
	link26_powerAlarm1R4 	OBJECT-TYPE    
    SYNTAX DisplayString
	MAX-ACCESS read-only
	STATUS current
    DESCRIPTION
        "Set The link26 1R4 Power Status Alarm."
    ::= {link26OBPTrap 32}
	
-- 1.3.6.1.4.1.47477.10.21.26.3.50.33
	link26_powerAlarm2R4 	OBJECT-TYPE    
    SYNTAX DisplayString
	MAX-ACCESS read-only
	STATUS current
    DESCRIPTION
        "Set The link26 2R4 Power Status Alarm."
    ::= {link26OBPTrap 33}
	
--  1.3.6.1.4.1.47477.10.21.27.3.1
		-- 1.3.6.1.4.1.47477.10.21.27.3.1
		link27_State OBJECT-TYPE
			SYNTAX INTEGER
				{
				off(0),
				on(1)
				}
			MAX-ACCESS read-only
			STATUS current
			DESCRIPTION
				"get the information about whether link27 is working."
			::= { link27OBP 1 }

		
--  1.3.6.1.4.1.47477.10.21.27.3.2
		-- 1.3.6.1.4.1.47477.10.21.27.3.2
		link27_DeviceType OBJECT-TYPE
			SYNTAX DisplayString
			MAX-ACCESS read-only
			STATUS current
			DESCRIPTION
				"get the type of card in link27."
			::= { link27OBP 2 }

			
--  1.3.6.1.4.1.47477.10.21.27.3.3
		-- 1.3.6.1.4.1.47477.10.21.27.3.3
		link27_WorkMode OBJECT-TYPE
			SYNTAX INTEGER
				{
				manualMode(0),
				autoMode(1)
				}
			MAX-ACCESS read-write
			STATUS current
			DESCRIPTION
				"get or set link27's work mode."
			::= { link27OBP 3 }

		
--  1.3.6.1.4.1.47477.10.21.27.3.4
		-- 1.3.6.1.4.1.47477.10.21.27.3.4
		link27_Channel OBJECT-TYPE
			SYNTAX INTEGER
				{
				bypass(0),
				primary(1)
				}
			MAX-ACCESS read-write
			STATUS current
			DESCRIPTION
				"get or set the channel in which link27 works."
			::= { link27OBP 4 }


--  1.3.6.1.4.1.47477.10.21.27.3.5
		-- 1.3.6.1.4.1.47477.10.21.27.3.5
		link27_R1Power OBJECT-TYPE
			SYNTAX DisplayString
			MAX-ACCESS read-only
			STATUS current
			DESCRIPTION
				"get the power of R1 in link27."
			::= { link27OBP 5 }

		
--  1.3.6.1.4.1.47477.10.21.27.3.6
		-- 1.3.6.1.4.1.47477.10.21.27.3.6
		link27_R2Power OBJECT-TYPE
			SYNTAX DisplayString
			MAX-ACCESS read-only
			STATUS current
			DESCRIPTION
				"get the power of R2 in link27."
			::= { link27OBP 6 }
			
--  1.3.6.1.4.1.47477.10.21.27.3.35
		-- 1.3.6.1.4.1.47477.10.21.27.3.35
		link27_R3Power OBJECT-TYPE
			SYNTAX DisplayString
			MAX-ACCESS read-only
			STATUS current
			DESCRIPTION
				"get the power of R3 in link27."
			::= { link27OBP 35 }
			
--  1.3.6.1.4.1.47477.10.21.27.3.36
		-- 1.3.6.1.4.1.47477.10.21.27.3.36
		link27_R4Power OBJECT-TYPE
			SYNTAX DisplayString
			MAX-ACCESS read-only
			STATUS current
			DESCRIPTION
				"get the power of R4 in link27."
			::= { link27OBP 36 }		
		
--  1.3.6.1.4.1.47477.10.21.27.3.7
		-- 1.3.6.1.4.1.47477.10.21.27.3.7
		link27_R1Wave OBJECT-TYPE
			SYNTAX INTEGER
				{
				w1310nm(0),
				w1550nm(1),
				na(2)
				}
			MAX-ACCESS read-write
			STATUS current
			DESCRIPTION
				"get or set the wave length of R1 in link27."
			::= { link27OBP 7 }

		
--  1.3.6.1.4.1.47477.10.21.27.3.8
		-- 1.3.6.1.4.1.47477.10.21.27.3.8
		link27_R2Wave OBJECT-TYPE
			SYNTAX INTEGER
				{
				w1310nm(0),
				w1550nm(1),
				na(2)
				}
			MAX-ACCESS read-write
			STATUS current
			DESCRIPTION
				"get or set the wave length of R2 in link27."
			::= { link27OBP 8 }


--  1.3.6.1.4.1.47477.10.21.27.3.27
		-- 1.3.6.1.4.1.47477.10.21.27.3.27
		link27_R3Wave OBJECT-TYPE
			SYNTAX INTEGER
				{
				w1310nm(0),
				w1550nm(1),
				na(2)
				}
			MAX-ACCESS read-write
			STATUS current
			DESCRIPTION
				"get or set the wave length of R3 in link27."
			::= { link27OBP 27 }

		
--  1.3.6.1.4.1.47477.10.21.27.3.28
		-- 1.3.6.1.4.1.47477.10.21.27.3.28
		link27_R4Wave OBJECT-TYPE
			SYNTAX INTEGER
				{
				w1310nm(0),
				w1550nm(1),
				na(2)
				}
			MAX-ACCESS read-write
			STATUS current
			DESCRIPTION
				"get or set the wave length of R4 in link27."
			::= { link27OBP 28 }
			
--  1.3.6.1.4.1.47477.10.21.27.3.9
		-- 1.3.6.1.4.1.47477.10.21.27.3.9
		link27_R1AlarmPower OBJECT-TYPE
			SYNTAX DisplayString
			MAX-ACCESS read-write
			STATUS current
			DESCRIPTION
				"get or set the power alarm threshold of R1 in link27."
			::= { link27OBP 9 }

		
--  1.3.6.1.4.1.47477.10.21.27.3.10
		-- 1.3.6.1.4.1.47477.10.21.27.3.10
		link27_R2AlarmPower OBJECT-TYPE
			SYNTAX DisplayString
			MAX-ACCESS read-write
			STATUS current
			DESCRIPTION
				"get or set the power alarm threshold of R2 in link27."
			::= { link27OBP 10 }


--  1.3.6.1.4.1.47477.10.21.27.3.29
		-- 1.3.6.1.4.1.47477.10.21.27.3.29
		link27_R3AlarmPower OBJECT-TYPE
			SYNTAX DisplayString
			MAX-ACCESS read-write
			STATUS current
			DESCRIPTION
				"get or set the power alarm threshold of R3 in link27."
			::= { link27OBP 29 }

		
--  1.3.6.1.4.1.47477.10.21.27.3.30
		-- 1.3.6.1.4.1.47477.10.21.27.3.30
		link27_R4AlarmPower OBJECT-TYPE
			SYNTAX DisplayString
			MAX-ACCESS read-write
			STATUS current
			DESCRIPTION
				"get or set the power alarm threshold of R4 in link27."
			::= { link27OBP 30 }

-- OBP4
--  1.3.6.1.4.1.47477.10.21.27.3.37
		-- 1.3.6.1.4.1.47477.10.21.27.3.37
		link27_1R1Power OBJECT-TYPE
			SYNTAX DisplayString
			MAX-ACCESS read-only
			STATUS current
			DESCRIPTION
				"get the power of 1R1 in link27."
			::= { link27OBP 37 }
			
--  1.3.6.1.4.1.47477.10.21.27.3.38
		-- 1.3.6.1.4.1.47477.10.21.27.3.38
		link27_1R2Power OBJECT-TYPE
			SYNTAX DisplayString
			MAX-ACCESS read-only
			STATUS current
			DESCRIPTION
				"get the power of 1R2 in link27."
			::= { link27OBP 38 }

--  1.3.6.1.4.1.47477.10.21.27.3.39
		-- 1.3.6.1.4.1.47477.10.21.27.3.39
		link27_1R3Power OBJECT-TYPE
			SYNTAX DisplayString
			MAX-ACCESS read-only
			STATUS current
			DESCRIPTION
				"get the power of 1R3 in link27."
			::= { link27OBP 39 }
			
--  1.3.6.1.4.1.47477.10.21.27.3.40
		-- 1.3.6.1.4.1.47477.10.21.27.3.40
		link27_1R4Power OBJECT-TYPE
			SYNTAX DisplayString
			MAX-ACCESS read-only
			STATUS current
			DESCRIPTION
				"get the power of 1R4 in link27."
			::= { link27OBP 40 }

--  1.3.6.1.4.1.47477.10.21.27.3.41
		-- 1.3.6.1.4.1.47477.10.21.27.3.41
		link27_2R1Power OBJECT-TYPE
			SYNTAX DisplayString
			MAX-ACCESS read-only
			STATUS current
			DESCRIPTION
				"get the power of 2R1 in link27."
			::= { link27OBP 41 }
			
--  1.3.6.1.4.1.47477.10.21.27.3.42
		-- 1.3.6.1.4.1.47477.10.21.27.3.42
		link27_2R2Power OBJECT-TYPE
			SYNTAX DisplayString
			MAX-ACCESS read-only
			STATUS current
			DESCRIPTION
				"get the power of 2R2 in link27."
			::= { link27OBP 42 }

--  1.3.6.1.4.1.47477.10.21.27.3.41
		-- 1.3.6.1.4.1.47477.10.21.27.3.43
		link27_2R3Power OBJECT-TYPE
			SYNTAX DisplayString
			MAX-ACCESS read-only
			STATUS current
			DESCRIPTION
				"get the power of 2R3 in link27."
			::= { link27OBP 43 }
			
--  1.3.6.1.4.1.47477.10.21.27.3.42
		-- 1.3.6.1.4.1.47477.10.21.27.3.44
		link27_2R4Power OBJECT-TYPE
			SYNTAX DisplayString
			MAX-ACCESS read-only
			STATUS current
			DESCRIPTION
				"get the power of 2R4 in link27."
			::= { link27OBP 44 }
			
--  1.3.6.1.4.1.47477.10.21.27.3.49
		-- 1.3.6.1.4.1.47477.10.21.27.3.49
		link27_1R1Wave OBJECT-TYPE
			SYNTAX INTEGER
				{
				w850nm(0),
				na(2)
				}
			MAX-ACCESS read-only
			STATUS current
			DESCRIPTION
				"get the wave length of 1R1 in link27."
			::= { link27OBP 49 }
		
--  1.3.6.1.4.1.47477.10.21.27.3.60
		-- 1.3.6.1.4.1.47477.10.21.27.3.60
		link27_1R2Wave OBJECT-TYPE
			SYNTAX INTEGER
				{
				w850nm(0),
				na(2)
				}
			MAX-ACCESS read-only
			STATUS current
			DESCRIPTION
				"get the wave length of 1R2 in link27."
			::= { link27OBP 60 }

--  1.3.6.1.4.1.47477.10.21.27.3.61
		-- 1.3.6.1.4.1.47477.10.21.27.3.61
		link27_1R3Wave OBJECT-TYPE
			SYNTAX INTEGER
				{
				w850nm(0),
				na(2)
				}
			MAX-ACCESS read-only
			STATUS current
			DESCRIPTION
				"get the wave length of 1R3 in link27."
			::= { link27OBP 61 }

		
--  1.3.6.1.4.1.47477.10.21.27.3.62
		-- 1.3.6.1.4.1.47477.10.21.27.3.62
		link27_1R4Wave OBJECT-TYPE
			SYNTAX INTEGER
				{
				w850nm(0),
				na(2)
				}
			MAX-ACCESS read-only
			STATUS current
			DESCRIPTION
				"get the wave length of 1R4 in link27."
			::= { link27OBP 62 }
	
--  1.3.6.1.4.1.47477.10.21.27.3.63
		-- 1.3.6.1.4.1.47477.10.21.27.3.63
		link27_2R1Wave OBJECT-TYPE
			SYNTAX INTEGER
				{
				w850nm(0),
				na(2)
				}
			MAX-ACCESS read-only
			STATUS current
			DESCRIPTION
				"get the wave length of 2R1 in link27."
			::= { link27OBP 63 }

		
--  1.3.6.1.4.1.47477.10.21.27.3.64
		-- 1.3.6.1.4.1.47477.10.21.27.3.64
		link27_2R2Wave OBJECT-TYPE
			SYNTAX INTEGER
				{
				w850nm(0),
				na(2)
				}
			MAX-ACCESS read-only
			STATUS current
			DESCRIPTION
				"get the wave length of 2R2 in link27."
			::= { link27OBP 64 }	
	
--  1.3.6.1.4.1.47477.10.21.27.3.65
		-- 1.3.6.1.4.1.47477.10.21.27.3.65
		link27_2R3Wave OBJECT-TYPE
			SYNTAX INTEGER
				{
				w850nm(0),
				na(2)
				}
			MAX-ACCESS read-only
			STATUS current
			DESCRIPTION
				"get the wave length of 2R3 in link27."
			::= { link27OBP 65 }

		
--  1.3.6.1.4.1.47477.10.21.27.3.66
		-- 1.3.6.1.4.1.47477.10.21.27.3.66
		link27_2R4Wave OBJECT-TYPE
			SYNTAX INTEGER
				{
				w850nm(0),
				na(2)
				}
			MAX-ACCESS read-only
			STATUS current
			DESCRIPTION
				"get the wave length of 2R4 in link27."
			::= { link27OBP 66 }	
			
--  1.3.6.1.4.1.47477.10.21.27.3.31
		-- 1.3.6.1.4.1.47477.10.21.27.3.31
		link27_1R1AlarmPower OBJECT-TYPE
			SYNTAX DisplayString
			MAX-ACCESS read-write
			STATUS current
			DESCRIPTION
				"get or set the power alarm threshold of 1R1 in link27."
			::= { link27OBP 31 }
			
--  1.3.6.1.4.1.47477.10.21.27.3.32
		-- 1.3.6.1.4.1.47477.10.21.27.3.32
		link27_1R2AlarmPower OBJECT-TYPE
			SYNTAX DisplayString
			MAX-ACCESS read-write
			STATUS current
			DESCRIPTION
				"get or set the power alarm threshold of 1R2 in link27."
			::= { link27OBP 32 }

--  1.3.6.1.4.1.47477.10.21.27.3.33
		-- 1.3.6.1.4.1.47477.10.21.27.3.33
		link27_1R3AlarmPower OBJECT-TYPE
			SYNTAX DisplayString
			MAX-ACCESS read-write
			STATUS current
			DESCRIPTION
				"get or set the power alarm threshold of 1R3 in link27."
			::= { link27OBP 33 }
			
--  1.3.6.1.4.1.47477.10.21.27.3.34
		-- 1.3.6.1.4.1.47477.10.21.27.3.34
		link27_1R4AlarmPower OBJECT-TYPE
			SYNTAX DisplayString
			MAX-ACCESS read-write
			STATUS current
			DESCRIPTION
				"get or set the power alarm threshold of 1R4 in link27."
			::= { link27OBP 34 }

--  1.3.6.1.4.1.47477.10.21.27.3.45
		-- 1.3.6.1.4.1.47477.10.21.27.3.45
		link27_2R1AlarmPower OBJECT-TYPE
			SYNTAX DisplayString
			MAX-ACCESS read-write
			STATUS current
			DESCRIPTION
				"get or set the power alarm threshold of 2R1 in link27."
			::= { link27OBP 45 }
			
--  1.3.6.1.4.1.47477.10.21.27.3.46
		-- 1.3.6.1.4.1.47477.10.21.27.3.46
		link27_2R2AlarmPower OBJECT-TYPE
			SYNTAX DisplayString
			MAX-ACCESS read-write
			STATUS current
			DESCRIPTION
				"get or set the power alarm threshold of 2R2 in link27."
			::= { link27OBP 46 }

--  1.3.6.1.4.1.47477.10.21.27.3.47
		-- 1.3.6.1.4.1.47477.10.21.27.3.47
		link27_2R3AlarmPower OBJECT-TYPE
			SYNTAX DisplayString
			MAX-ACCESS read-write
			STATUS current
			DESCRIPTION
				"get or set the power alarm threshold of 2R3 in link27."
			::= { link27OBP 47 }
			
--  1.3.6.1.4.1.47477.10.21.27.3.48
		-- 1.3.6.1.4.1.47477.10.21.27.3.48
		link27_2R4AlarmPower OBJECT-TYPE
			SYNTAX DisplayString
			MAX-ACCESS read-write
			STATUS current
			DESCRIPTION
				"get or set the power alarm threshold of 2R4 in link27."
			::= { link27OBP 48 }
			
--  1.3.6.1.4.1.47477.10.21.27.3.11
		-- 1.3.6.1.4.1.47477.10.21.27.3.11
		link27_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link27OBP 11 }
			
--  1.3.6.1.4.1.47477.10.21.27.3.67
		-- 1.3.6.1.4.1.47477.10.21.27.3.67
		link27_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link27OBP 67 }
			
--  1.3.6.1.4.1.47477.10.21.27.3.68
		-- 1.3.6.1.4.1.47477.10.21.27.3.68
		link27_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link27OBP 68 }
			
--  1.3.6.1.4.1.47477.10.21.27.3.12
		-- 1.3.6.1.4.1.47477.10.21.27.3.12
		link27_ReturnDelay OBJECT-TYPE
			--SYNTAX Integer32
			SYNTAX Integer32
			MAX-ACCESS read-write
			STATUS current
			DESCRIPTION
				"get or set how long link27 takes to return to automatic mode."
			::= { link27OBP 12 }
			
--  1.3.6.1.4.1.47477.10.21.27.3.13
		-- 1.3.6.1.4.1.47477.10.21.27.3.13
		link27_BackMode OBJECT-TYPE
			SYNTAX INTEGER
				{
				autoNoBack(0),
				autoBack(1)
				}
			MAX-ACCESS read-write
			STATUS current
			DESCRIPTION
				"get or set the back mode of link27."
			::= { link27OBP 13 }

		
--  1.3.6.1.4.1.47477.10.21.27.3.14
		-- 1.3.6.1.4.1.47477.10.21.27.3.14
		link27_BackDelay OBJECT-TYPE
			SYNTAX Integer32
			MAX-ACCESS read-write
			STATUS current
			DESCRIPTION
				"get or set the back delay."
			::= { link27OBP 14 }

--  1.3.6.1.4.1.47477.10.21.27.3.15
		-- 1.3.6.1.4.1.47477.10.21.27.3.15
		link27_ActiveHeartSwitch OBJECT-TYPE
			SYNTAX INTEGER
				{
				off(0),
				on(1)
				}
			MAX-ACCESS read-write
			STATUS current
			DESCRIPTION
				"get or set the switch status of active heartbeat."
			::= { link27OBP 15 }

		
--  1.3.6.1.4.1.47477.10.21.27.3.16
		-- 1.3.6.1.4.1.47477.10.21.27.3.16
		link27_ActiveSendInterval OBJECT-TYPE
			SYNTAX Integer32
			MAX-ACCESS read-write
			STATUS current
			DESCRIPTION
				"get or set the send interval of active heartbeat."
			::= { link27OBP 16 }		

--  1.3.6.1.4.1.47477.10.21.27.3.17
		-- 1.3.6.1.4.1.47477.10.21.27.3.17
		link27_ActiveTimeOut OBJECT-TYPE
			SYNTAX Integer32
			MAX-ACCESS read-write
			STATUS current
			DESCRIPTION
				"get or set how long the active heartbeat send timeout."
			::= { link27OBP 17 }

--  1.3.6.1.4.1.47477.10.21.27.3.18
		-- 1.3.6.1.4.1.47477.10.21.27.3.18
		link27_ActiveLossBypass OBJECT-TYPE
			SYNTAX Integer32
			MAX-ACCESS read-write
			STATUS current
			DESCRIPTION
				"get or set the bypass for active heartbeat packet loss."
			::= { link27OBP 18 }

--  1.3.6.1.4.1.47477.10.21.27.3.19
		-- 1.3.6.1.4.1.47477.10.21.27.3.19
		link27_PingIpAddress OBJECT-TYPE
			SYNTAX IpAddress
			MAX-ACCESS read-write
			STATUS current
			DESCRIPTION
				"get or set the ping ip address of link27."
			::= { link27OBP 19 }

--  1.3.6.1.4.1.47477.10.21.27.3.20
		-- 1.3.6.1.4.1.47477.10.21.27.3.20
		link27_PassiveHeartSwitch OBJECT-TYPE
			SYNTAX INTEGER
				{
				off(0),
				on(1)
				}
			MAX-ACCESS read-write
			STATUS current
			DESCRIPTION
				"get or set the switch status of passive heartbeat."
			::= { link27OBP 20 }
	

--  1.3.6.1.4.1.47477.10.21.27.3.21
		-- 1.3.6.1.4.1.47477.10.21.27.3.21
		link27_PassiveTimeOut OBJECT-TYPE
			SYNTAX Integer32
			MAX-ACCESS read-write
			STATUS current
			DESCRIPTION
				"get or set how long the passive heartbeat send timeout."
			::= { link27OBP 21 }

--  1.3.6.1.4.1.47477.10.21.27.3.22
		-- 1.3.6.1.4.1.47477.10.21.27.3.22
		link27_PassiveLossBypass OBJECT-TYPE
			SYNTAX Integer32
			MAX-ACCESS read-write
			STATUS current
			DESCRIPTION
				"get or set the bypass for passive heartbeat packet loss."
			::= { link27OBP 22 }

--  1.3.6.1.4.1.47477.10.21.27.3.23
		-- 1.3.6.1.4.1.47477.10.21.27.3.23
		link27_SwitchProtect OBJECT-TYPE
			SYNTAX INTEGER
				{
				off(0),
				on(1)
				}
			MAX-ACCESS read-write
			STATUS current
			DESCRIPTION
				"get or set the switch protection status of link27."
			::= { link27OBP 23 }
			
--  1.3.6.1.4.1.47477.10.21.27.3.24
		-- 1.3.6.1.4.1.47477.10.21.27.3.24
		link27_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link27OBP 24 }		

--  1.3.6.1.4.1.47477.10.21.27.3.25
		-- 1.3.6.1.4.1.47477.10.21.27.3.25
		link27_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link27OBP 25 }	

--  1.3.6.1.4.1.47477.10.21.27.3.26
		-- 1.3.6.1.4.1.47477.10.21.27.3.26
		link27_PowerAlarmStatus OBJECT-TYPE
			SYNTAX INTEGER
				{
				off(0),
				alarm(1),
				normal(2),
				na(3)
				}
			MAX-ACCESS read-only
			STATUS current
			DESCRIPTION
				"get whether a power alarm is generated."
			::= { link27OBP 26 }	


-- 1.3.6.1.4.1.47477.10.21.27.3.50.1
	link27_WorkModeChange 	OBJECT-TYPE    
    SYNTAX INTEGER	{
				manualMode(0),
				autoMode(1)
		}
	MAX-ACCESS read-only
	STATUS current
    DESCRIPTION
        "The Link mode Changed."
    ::= {link27OBPTrap 1}

-- 1.3.6.1.4.1.47477.10.21.27.3.50.2
	link27_StateChange 	OBJECT-TYPE    
    SYNTAX INTEGER	{
				bypass(0),
				primary(1)
		}
	MAX-ACCESS read-only
	STATUS current
    DESCRIPTION
        "The Link State(Channel) Changed."
    ::= {link27OBPTrap 2}

-- 1.3.6.1.4.1.47477.10.21.27.3.50.3
	link27_R1WaveSet 	OBJECT-TYPE    
    SYNTAX INTEGER	{
				w1310nm(0),
				w1550nm(1)
		}
	MAX-ACCESS read-only
	STATUS current
    DESCRIPTION
        "Set The link27 R1 Wave."
    ::= {link27OBPTrap 3}

-- 1.3.6.1.4.1.47477.10.21.27.3.50.4
	link27_R2WaveSet 	OBJECT-TYPE    
    SYNTAX INTEGER	{
				w1310nm(0),
				w1550nm(1)
		}
	MAX-ACCESS read-only
	STATUS current
    DESCRIPTION
        "Set The link27 R2 Wave."
    ::= {link27OBPTrap 4}			

-- 1.3.6.1.4.1.47477.10.21.27.3.50.5
	link27_R3WaveSet 	OBJECT-TYPE    
    SYNTAX INTEGER	{
				w1310nm(0),
				w1550nm(1)
		}
	MAX-ACCESS read-only
	STATUS current
    DESCRIPTION
        "Set The link27 R3 Wave."
    ::= {link27OBPTrap 5}

-- 1.3.6.1.4.1.47477.10.21.27.3.50.6
	link27_R4WaveSet 	OBJECT-TYPE    
    SYNTAX INTEGER	{
				w1310nm(0),
				w1550nm(1)
		}
	MAX-ACCESS read-only
	STATUS current
    DESCRIPTION
        "Set The link27 R4 Wave."
    ::= {link27OBPTrap 6}	
	
-- 1.3.6.1.4.1.47477.10.21.27.3.50.7
	link27_R1AlarmSet 	OBJECT-TYPE    
    SYNTAX DisplayString
	MAX-ACCESS read-only
	STATUS current
    DESCRIPTION
        "Set The link27 R1 Alarm Threshold."
    ::= {link27OBPTrap 7}

-- 1.3.6.1.4.1.47477.10.21.27.3.50.8
	link27_R2AlarmSet 	OBJECT-TYPE    
    SYNTAX DisplayString
	MAX-ACCESS read-only
	STATUS current
    DESCRIPTION
        "Set The link27 R2 Alarm Threshold."
    ::= {link27OBPTrap 8}
	
-- 1.3.6.1.4.1.47477.10.21.27.3.50.9
	link27_R3AlarmSet 	OBJECT-TYPE    
    SYNTAX DisplayString
	MAX-ACCESS read-only
	STATUS current
    DESCRIPTION
        "Set The link27 R3 Alarm Threshold."
    ::= {link27OBPTrap 9}

-- 1.3.6.1.4.1.47477.10.21.27.3.50.10
	link27_R4AlarmSet 	OBJECT-TYPE    
    SYNTAX DisplayString
	MAX-ACCESS read-only
	STATUS current
    DESCRIPTION
        "Set The link27 R4 Alarm Threshold."
    ::= {link27OBPTrap 10}	
	
	
-- 1.3.6.1.4.1.47477.10.21.27.3.50.11
	link27_1R1AlarmSet 	OBJECT-TYPE    
    SYNTAX DisplayString
	MAX-ACCESS read-only
	STATUS current
    DESCRIPTION
        "Set The link27 1R1 Alarm Threshold."
    ::= {link27OBPTrap 11}

-- 1.3.6.1.4.1.47477.10.21.27.3.50.12
	link27_2R1AlarmSet 	OBJECT-TYPE    
    SYNTAX DisplayString
	MAX-ACCESS read-only
	STATUS current
    DESCRIPTION
        "Set The link27 2R1 Alarm Threshold."
    ::= {link27OBPTrap 12}
	
-- 1.3.6.1.4.1.47477.10.21.27.3.50.13
	link27_1R2AlarmSet 	OBJECT-TYPE    
    SYNTAX DisplayString
	MAX-ACCESS read-only
	STATUS current
    DESCRIPTION
        "Set The link27 1R2 Alarm Threshold."
    ::= {link27OBPTrap 13}

-- 1.3.6.1.4.1.47477.10.21.27.3.50.14
	link27_2R2AlarmSet 	OBJECT-TYPE    
    SYNTAX DisplayString
	MAX-ACCESS read-only
	STATUS current
    DESCRIPTION
        "Set The link27 2R2 Alarm Threshold."
    ::= {link27OBPTrap 14}
	
-- 1.3.6.1.4.1.47477.10.21.27.3.50.15
	link27_1R3AlarmSet 	OBJECT-TYPE    
    SYNTAX DisplayString
	MAX-ACCESS read-only
	STATUS current
    DESCRIPTION
        "Set The link27 1R3 Alarm Threshold."
    ::= {link27OBPTrap 15}

-- 1.3.6.1.4.1.47477.10.21.27.3.50.16
	link27_2R3AlarmSet 	OBJECT-TYPE    
    SYNTAX DisplayString
	MAX-ACCESS read-only
	STATUS current
    DESCRIPTION
        "Set The link27 2R3 Alarm Threshold."
    ::= {link27OBPTrap 16}
	
-- 1.3.6.1.4.1.47477.10.21.27.3.50.17
	link27_1R4AlarmSet 	OBJECT-TYPE    
    SYNTAX DisplayString
	MAX-ACCESS read-only
	STATUS current
    DESCRIPTION
        "Set The link27 1R4 Alarm Threshold."
    ::= {link27OBPTrap 17}

-- 1.3.6.1.4.1.47477.10.21.27.3.50.18
	link27_2R4AlarmSet 	OBJECT-TYPE    
    SYNTAX DisplayString
	MAX-ACCESS read-only
	STATUS current
    DESCRIPTION
        "Set The link27 2R4 Alarm Threshold."
    ::= {link27OBPTrap 18}
	
-- 1.3.6.1.4.1.47477.10.21.27.3.50.19
	link27_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link27 PowerAlarmBypass2 Changed."
    ::= {link27OBPTrap 19}
	
-- 1.3.6.1.4.1.47477.10.21.27.3.50.20
	link27_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link27 PowerAlarmBypass4 Changed."
    ::= {link27OBPTrap 20}	
	
-- 1.3.6.1.4.1.47477.10.21.27.3.50.21
	link27_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link27 PowerAlarmBypass8 Changed."
    ::= {link27OBPTrap 21}
	
-- 1.3.6.1.4.1.47477.10.21.27.3.50.22
	link27_powerAlarmR1 	OBJECT-TYPE    
    SYNTAX DisplayString
	MAX-ACCESS read-only
	STATUS current
    DESCRIPTION
        "Set The link27 R1 Power Status Alarm."
    ::= {link27OBPTrap 22}
	
-- 1.3.6.1.4.1.47477.10.21.27.3.50.23
	link27_powerAlarmR2 	OBJECT-TYPE    
    SYNTAX DisplayString
	MAX-ACCESS read-only
	STATUS current
    DESCRIPTION
        "Set The link27 R2 Power Status Alarm."
    ::= {link27OBPTrap 23}
	
-- 1.3.6.1.4.1.47477.10.21.27.3.50.24
	link27_powerAlarmR3 	OBJECT-TYPE    
    SYNTAX DisplayString
	MAX-ACCESS read-only
	STATUS current
    DESCRIPTION
        "Set The link27 R3 Power Status Alarm."
    ::= {link27OBPTrap 24}
	
-- 1.3.6.1.4.1.47477.10.21.27.3.50.25
	link27_powerAlarmR4 	OBJECT-TYPE    
    SYNTAX DisplayString
	MAX-ACCESS read-only
	STATUS current
    DESCRIPTION
        "Set The link27 R4 Power Status Alarm."
    ::= {link27OBPTrap 25}
	
	
-- 1.3.6.1.4.1.47477.10.21.27.3.50.26
	link27_powerAlarm1R1 	OBJECT-TYPE    
    SYNTAX DisplayString
	MAX-ACCESS read-only
	STATUS current
    DESCRIPTION
        "Set The link27 1R1 Power Status Alarm."
    ::= {link27OBPTrap 26}
	
-- 1.3.6.1.4.1.47477.10.21.27.3.50.27
	link27_powerAlarm2R1 	OBJECT-TYPE    
    SYNTAX DisplayString
	MAX-ACCESS read-only
	STATUS current
    DESCRIPTION
        "Set The link27 2R1 Power Status Alarm."
    ::= {link27OBPTrap 27}
	
-- 1.3.6.1.4.1.47477.10.21.27.3.50.28
	link27_powerAlarm1R2 	OBJECT-TYPE    
    SYNTAX DisplayString
	MAX-ACCESS read-only
	STATUS current
    DESCRIPTION
        "Set The link27 1R2 Power Status Alarm."
    ::= {link27OBPTrap 28}
	
-- 1.3.6.1.4.1.47477.10.21.27.3.50.29
	link27_powerAlarm2R2 	OBJECT-TYPE    
    SYNTAX DisplayString
	MAX-ACCESS read-only
	STATUS current
    DESCRIPTION
        "Set The link27 2R2 Power Status Alarm."
    ::= {link27OBPTrap 29}
	
-- 1.3.6.1.4.1.47477.10.21.27.3.50.30
	link27_powerAlarm1R3 	OBJECT-TYPE    
    SYNTAX DisplayString
	MAX-ACCESS read-only
	STATUS current
    DESCRIPTION
        "Set The link27 1R3 Power Status Alarm."
    ::= {link27OBPTrap 30}
	
-- 1.3.6.1.4.1.47477.10.21.27.3.50.31
	link27_powerAlarm2R3 	OBJECT-TYPE    
    SYNTAX DisplayString
	MAX-ACCESS read-only
	STATUS current
    DESCRIPTION
        "Set The link27 2R1 Power Status Alarm."
    ::= {link27OBPTrap 31}
	
-- 1.3.6.1.4.1.47477.10.21.27.3.50.32
	link27_powerAlarm1R4 	OBJECT-TYPE    
    SYNTAX DisplayString
	MAX-ACCESS read-only
	STATUS current
    DESCRIPTION
        "Set The link27 1R4 Power Status Alarm."
    ::= {link27OBPTrap 32}
	
-- 1.3.6.1.4.1.47477.10.21.27.3.50.33
	link27_powerAlarm2R4 	OBJECT-TYPE    
    SYNTAX DisplayString
	MAX-ACCESS read-only
	STATUS current
    DESCRIPTION
        "Set The link27 2R4 Power Status Alarm."
    ::= {link27OBPTrap 33}
	
--  1.3.6.1.4.1.47477.10.21.28.3.1
		-- 1.3.6.1.4.1.47477.10.21.28.3.1
		link28_State OBJECT-TYPE
			SYNTAX INTEGER
				{
				off(0),
				on(1)
				}
			MAX-ACCESS read-only
			STATUS current
			DESCRIPTION
				"get the information about whether link28 is working."
			::= { link28OBP 1 }

		
--  1.3.6.1.4.1.47477.10.21.28.3.2
		-- 1.3.6.1.4.1.47477.10.21.28.3.2
		link28_DeviceType OBJECT-TYPE
			SYNTAX DisplayString
			MAX-ACCESS read-only
			STATUS current
			DESCRIPTION
				"get the type of card in link28."
			::= { link28OBP 2 }

			
--  1.3.6.1.4.1.47477.10.21.28.3.3
		-- 1.3.6.1.4.1.47477.10.21.28.3.3
		link28_WorkMode OBJECT-TYPE
			SYNTAX INTEGER
				{
				manualMode(0),
				autoMode(1)
				}
			MAX-ACCESS read-write
			STATUS current
			DESCRIPTION
				"get or set link28's work mode."
			::= { link28OBP 3 }

		
--  1.3.6.1.4.1.47477.10.21.28.3.4
		-- 1.3.6.1.4.1.47477.10.21.28.3.4
		link28_Channel OBJECT-TYPE
			SYNTAX INTEGER
				{
				bypass(0),
				primary(1)
				}
			MAX-ACCESS read-write
			STATUS current
			DESCRIPTION
				"get or set the channel in which link28 works."
			::= { link28OBP 4 }


--  1.3.6.1.4.1.47477.10.21.28.3.5
		-- 1.3.6.1.4.1.47477.10.21.28.3.5
		link28_R1Power OBJECT-TYPE
			SYNTAX DisplayString
			MAX-ACCESS read-only
			STATUS current
			DESCRIPTION
				"get the power of R1 in link28."
			::= { link28OBP 5 }

		
--  1.3.6.1.4.1.47477.10.21.28.3.6
		-- 1.3.6.1.4.1.47477.10.21.28.3.6
		link28_R2Power OBJECT-TYPE
			SYNTAX DisplayString
			MAX-ACCESS read-only
			STATUS current
			DESCRIPTION
				"get the power of R2 in link28."
			::= { link28OBP 6 }
			
--  1.3.6.1.4.1.47477.10.21.28.3.35
		-- 1.3.6.1.4.1.47477.10.21.28.3.35
		link28_R3Power OBJECT-TYPE
			SYNTAX DisplayString
			MAX-ACCESS read-only
			STATUS current
			DESCRIPTION
				"get the power of R3 in link28."
			::= { link28OBP 35 }
			
--  1.3.6.1.4.1.47477.10.21.28.3.36
		-- 1.3.6.1.4.1.47477.10.21.28.3.36
		link28_R4Power OBJECT-TYPE
			SYNTAX DisplayString
			MAX-ACCESS read-only
			STATUS current
			DESCRIPTION
				"get the power of R4 in link28."
			::= { link28OBP 36 }		
		
--  1.3.6.1.4.1.47477.10.21.28.3.7
		-- 1.3.6.1.4.1.47477.10.21.28.3.7
		link28_R1Wave OBJECT-TYPE
			SYNTAX INTEGER
				{
				w1310nm(0),
				w1550nm(1),
				na(2)
				}
			MAX-ACCESS read-write
			STATUS current
			DESCRIPTION
				"get or set the wave length of R1 in link28."
			::= { link28OBP 7 }

		
--  1.3.6.1.4.1.47477.10.21.28.3.8
		-- 1.3.6.1.4.1.47477.10.21.28.3.8
		link28_R2Wave OBJECT-TYPE
			SYNTAX INTEGER
				{
				w1310nm(0),
				w1550nm(1),
				na(2)
				}
			MAX-ACCESS read-write
			STATUS current
			DESCRIPTION
				"get or set the wave length of R2 in link28."
			::= { link28OBP 8 }


--  1.3.6.1.4.1.47477.10.21.28.3.27
		-- 1.3.6.1.4.1.47477.10.21.28.3.27
		link28_R3Wave OBJECT-TYPE
			SYNTAX INTEGER
				{
				w1310nm(0),
				w1550nm(1),
				na(2)
				}
			MAX-ACCESS read-write
			STATUS current
			DESCRIPTION
				"get or set the wave length of R3 in link28."
			::= { link28OBP 27 }

		
--  1.3.6.1.4.1.47477.10.21.28.3.28
		-- 1.3.6.1.4.1.47477.10.21.28.3.28
		link28_R4Wave OBJECT-TYPE
			SYNTAX INTEGER
				{
				w1310nm(0),
				w1550nm(1),
				na(2)
				}
			MAX-ACCESS read-write
			STATUS current
			DESCRIPTION
				"get or set the wave length of R4 in link28."
			::= { link28OBP 28 }
			
--  1.3.6.1.4.1.47477.10.21.28.3.9
		-- 1.3.6.1.4.1.47477.10.21.28.3.9
		link28_R1AlarmPower OBJECT-TYPE
			SYNTAX DisplayString
			MAX-ACCESS read-write
			STATUS current
			DESCRIPTION
				"get or set the power alarm threshold of R1 in link28."
			::= { link28OBP 9 }

		
--  1.3.6.1.4.1.47477.10.21.28.3.10
		-- 1.3.6.1.4.1.47477.10.21.28.3.10
		link28_R2AlarmPower OBJECT-TYPE
			SYNTAX DisplayString
			MAX-ACCESS read-write
			STATUS current
			DESCRIPTION
				"get or set the power alarm threshold of R2 in link28."
			::= { link28OBP 10 }


--  1.3.6.1.4.1.47477.10.21.28.3.29
		-- 1.3.6.1.4.1.47477.10.21.28.3.29
		link28_R3AlarmPower OBJECT-TYPE
			SYNTAX DisplayString
			MAX-ACCESS read-write
			STATUS current
			DESCRIPTION
				"get or set the power alarm threshold of R3 in link28."
			::= { link28OBP 29 }

		
--  1.3.6.1.4.1.47477.10.21.28.3.30
		-- 1.3.6.1.4.1.47477.10.21.28.3.30
		link28_R4AlarmPower OBJECT-TYPE
			SYNTAX DisplayString
			MAX-ACCESS read-write
			STATUS current
			DESCRIPTION
				"get or set the power alarm threshold of R4 in link28."
			::= { link28OBP 30 }

-- OBP4
--  1.3.6.1.4.1.47477.10.21.28.3.37
		-- 1.3.6.1.4.1.47477.10.21.28.3.37
		link28_1R1Power OBJECT-TYPE
			SYNTAX DisplayString
			MAX-ACCESS read-only
			STATUS current
			DESCRIPTION
				"get the power of 1R1 in link28."
			::= { link28OBP 37 }
			
--  1.3.6.1.4.1.47477.10.21.28.3.38
		-- 1.3.6.1.4.1.47477.10.21.28.3.38
		link28_1R2Power OBJECT-TYPE
			SYNTAX DisplayString
			MAX-ACCESS read-only
			STATUS current
			DESCRIPTION
				"get the power of 1R2 in link28."
			::= { link28OBP 38 }

--  1.3.6.1.4.1.47477.10.21.28.3.39
		-- 1.3.6.1.4.1.47477.10.21.28.3.39
		link28_1R3Power OBJECT-TYPE
			SYNTAX DisplayString
			MAX-ACCESS read-only
			STATUS current
			DESCRIPTION
				"get the power of 1R3 in link28."
			::= { link28OBP 39 }
			
--  1.3.6.1.4.1.47477.10.21.28.3.40
		-- 1.3.6.1.4.1.47477.10.21.28.3.40
		link28_1R4Power OBJECT-TYPE
			SYNTAX DisplayString
			MAX-ACCESS read-only
			STATUS current
			DESCRIPTION
				"get the power of 1R4 in link28."
			::= { link28OBP 40 }

--  1.3.6.1.4.1.47477.10.21.28.3.41
		-- 1.3.6.1.4.1.47477.10.21.28.3.41
		link28_2R1Power OBJECT-TYPE
			SYNTAX DisplayString
			MAX-ACCESS read-only
			STATUS current
			DESCRIPTION
				"get the power of 2R1 in link28."
			::= { link28OBP 41 }
			
--  1.3.6.1.4.1.47477.10.21.28.3.42
		-- 1.3.6.1.4.1.47477.10.21.28.3.42
		link28_2R2Power OBJECT-TYPE
			SYNTAX DisplayString
			MAX-ACCESS read-only
			STATUS current
			DESCRIPTION
				"get the power of 2R2 in link28."
			::= { link28OBP 42 }

--  1.3.6.1.4.1.47477.10.21.28.3.41
		-- 1.3.6.1.4.1.47477.10.21.28.3.43
		link28_2R3Power OBJECT-TYPE
			SYNTAX DisplayString
			MAX-ACCESS read-only
			STATUS current
			DESCRIPTION
				"get the power of 2R3 in link28."
			::= { link28OBP 43 }
			
--  1.3.6.1.4.1.47477.10.21.28.3.42
		-- 1.3.6.1.4.1.47477.10.21.28.3.44
		link28_2R4Power OBJECT-TYPE
			SYNTAX DisplayString
			MAX-ACCESS read-only
			STATUS current
			DESCRIPTION
				"get the power of 2R4 in link28."
			::= { link28OBP 44 }
			
--  1.3.6.1.4.1.47477.10.21.28.3.49
		-- 1.3.6.1.4.1.47477.10.21.28.3.49
		link28_1R1Wave OBJECT-TYPE
			SYNTAX INTEGER
				{
				w850nm(0),
				na(2)
				}
			MAX-ACCESS read-only
			STATUS current
			DESCRIPTION
				"get the wave length of 1R1 in link28."
			::= { link28OBP 49 }
		
--  1.3.6.1.4.1.47477.10.21.28.3.60
		-- 1.3.6.1.4.1.47477.10.21.28.3.60
		link28_1R2Wave OBJECT-TYPE
			SYNTAX INTEGER
				{
				w850nm(0),
				na(2)
				}
			MAX-ACCESS read-only
			STATUS current
			DESCRIPTION
				"get the wave length of 1R2 in link28."
			::= { link28OBP 60 }

--  1.3.6.1.4.1.47477.10.21.28.3.61
		-- 1.3.6.1.4.1.47477.10.21.28.3.61
		link28_1R3Wave OBJECT-TYPE
			SYNTAX INTEGER
				{
				w850nm(0),
				na(2)
				}
			MAX-ACCESS read-only
			STATUS current
			DESCRIPTION
				"get the wave length of 1R3 in link28."
			::= { link28OBP 61 }

		
--  1.3.6.1.4.1.47477.10.21.28.3.62
		-- 1.3.6.1.4.1.47477.10.21.28.3.62
		link28_1R4Wave OBJECT-TYPE
			SYNTAX INTEGER
				{
				w850nm(0),
				na(2)
				}
			MAX-ACCESS read-only
			STATUS current
			DESCRIPTION
				"get the wave length of 1R4 in link28."
			::= { link28OBP 62 }
	
--  1.3.6.1.4.1.47477.10.21.28.3.63
		-- 1.3.6.1.4.1.47477.10.21.28.3.63
		link28_2R1Wave OBJECT-TYPE
			SYNTAX INTEGER
				{
				w850nm(0),
				na(2)
				}
			MAX-ACCESS read-only
			STATUS current
			DESCRIPTION
				"get the wave length of 2R1 in link28."
			::= { link28OBP 63 }

		
--  1.3.6.1.4.1.47477.10.21.28.3.64
		-- 1.3.6.1.4.1.47477.10.21.28.3.64
		link28_2R2Wave OBJECT-TYPE
			SYNTAX INTEGER
				{
				w850nm(0),
				na(2)
				}
			MAX-ACCESS read-only
			STATUS current
			DESCRIPTION
				"get the wave length of 2R2 in link28."
			::= { link28OBP 64 }	
	
--  1.3.6.1.4.1.47477.10.21.28.3.65
		-- 1.3.6.1.4.1.47477.10.21.28.3.65
		link28_2R3Wave OBJECT-TYPE
			SYNTAX INTEGER
				{
				w850nm(0),
				na(2)
				}
			MAX-ACCESS read-only
			STATUS current
			DESCRIPTION
				"get the wave length of 2R3 in link28."
			::= { link28OBP 65 }

		
--  1.3.6.1.4.1.47477.10.21.28.3.66
		-- 1.3.6.1.4.1.47477.10.21.28.3.66
		link28_2R4Wave OBJECT-TYPE
			SYNTAX INTEGER
				{
				w850nm(0),
				na(2)
				}
			MAX-ACCESS read-only
			STATUS current
			DESCRIPTION
				"get the wave length of 2R4 in link28."
			::= { link28OBP 66 }	
			
--  1.3.6.1.4.1.47477.10.21.28.3.31
		-- 1.3.6.1.4.1.47477.10.21.28.3.31
		link28_1R1AlarmPower OBJECT-TYPE
			SYNTAX DisplayString
			MAX-ACCESS read-write
			STATUS current
			DESCRIPTION
				"get or set the power alarm threshold of 1R1 in link28."
			::= { link28OBP 31 }
			
--  1.3.6.1.4.1.47477.10.21.28.3.32
		-- 1.3.6.1.4.1.47477.10.21.28.3.32
		link28_1R2AlarmPower OBJECT-TYPE
			SYNTAX DisplayString
			MAX-ACCESS read-write
			STATUS current
			DESCRIPTION
				"get or set the power alarm threshold of 1R2 in link28."
			::= { link28OBP 32 }

--  1.3.6.1.4.1.47477.10.21.28.3.33
		-- 1.3.6.1.4.1.47477.10.21.28.3.33
		link28_1R3AlarmPower OBJECT-TYPE
			SYNTAX DisplayString
			MAX-ACCESS read-write
			STATUS current
			DESCRIPTION
				"get or set the power alarm threshold of 1R3 in link28."
			::= { link28OBP 33 }
			
--  1.3.6.1.4.1.47477.10.21.28.3.34
		-- 1.3.6.1.4.1.47477.10.21.28.3.34
		link28_1R4AlarmPower OBJECT-TYPE
			SYNTAX DisplayString
			MAX-ACCESS read-write
			STATUS current
			DESCRIPTION
				"get or set the power alarm threshold of 1R4 in link28."
			::= { link28OBP 34 }

--  1.3.6.1.4.1.47477.10.21.28.3.45
		-- 1.3.6.1.4.1.47477.10.21.28.3.45
		link28_2R1AlarmPower OBJECT-TYPE
			SYNTAX DisplayString
			MAX-ACCESS read-write
			STATUS current
			DESCRIPTION
				"get or set the power alarm threshold of 2R1 in link28."
			::= { link28OBP 45 }
			
--  1.3.6.1.4.1.47477.10.21.28.3.46
		-- 1.3.6.1.4.1.47477.10.21.28.3.46
		link28_2R2AlarmPower OBJECT-TYPE
			SYNTAX DisplayString
			MAX-ACCESS read-write
			STATUS current
			DESCRIPTION
				"get or set the power alarm threshold of 2R2 in link28."
			::= { link28OBP 46 }

--  1.3.6.1.4.1.47477.10.21.28.3.47
		-- 1.3.6.1.4.1.47477.10.21.28.3.47
		link28_2R3AlarmPower OBJECT-TYPE
			SYNTAX DisplayString
			MAX-ACCESS read-write
			STATUS current
			DESCRIPTION
				"get or set the power alarm threshold of 2R3 in link28."
			::= { link28OBP 47 }
			
--  1.3.6.1.4.1.47477.10.21.28.3.48
		-- 1.3.6.1.4.1.47477.10.21.28.3.48
		link28_2R4AlarmPower OBJECT-TYPE
			SYNTAX DisplayString
			MAX-ACCESS read-write
			STATUS current
			DESCRIPTION
				"get or set the power alarm threshold of 2R4 in link28."
			::= { link28OBP 48 }
			
--  1.3.6.1.4.1.47477.10.21.28.3.11
		-- 1.3.6.1.4.1.47477.10.21.28.3.11
		link28_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link28OBP 11 }
			
--  1.3.6.1.4.1.47477.10.21.28.3.67
		-- 1.3.6.1.4.1.47477.10.21.28.3.67
		link28_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link28OBP 67 }
			
--  1.3.6.1.4.1.47477.10.21.28.3.68
		-- 1.3.6.1.4.1.47477.10.21.28.3.68
		link28_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link28OBP 68 }
			
--  1.3.6.1.4.1.47477.10.21.28.3.12
		-- 1.3.6.1.4.1.47477.10.21.28.3.12
		link28_ReturnDelay OBJECT-TYPE
			--SYNTAX Integer32
			SYNTAX Integer32
			MAX-ACCESS read-write
			STATUS current
			DESCRIPTION
				"get or set how long link28 takes to return to automatic mode."
			::= { link28OBP 12 }
			
--  1.3.6.1.4.1.47477.10.21.28.3.13
		-- 1.3.6.1.4.1.47477.10.21.28.3.13
		link28_BackMode OBJECT-TYPE
			SYNTAX INTEGER
				{
				autoNoBack(0),
				autoBack(1)
				}
			MAX-ACCESS read-write
			STATUS current
			DESCRIPTION
				"get or set the back mode of link28."
			::= { link28OBP 13 }

		
--  1.3.6.1.4.1.47477.10.21.28.3.14
		-- 1.3.6.1.4.1.47477.10.21.28.3.14
		link28_BackDelay OBJECT-TYPE
			SYNTAX Integer32
			MAX-ACCESS read-write
			STATUS current
			DESCRIPTION
				"get or set the back delay."
			::= { link28OBP 14 }

--  1.3.6.1.4.1.47477.10.21.28.3.15
		-- 1.3.6.1.4.1.47477.10.21.28.3.15
		link28_ActiveHeartSwitch OBJECT-TYPE
			SYNTAX INTEGER
				{
				off(0),
				on(1)
				}
			MAX-ACCESS read-write
			STATUS current
			DESCRIPTION
				"get or set the switch status of active heartbeat."
			::= { link28OBP 15 }

		
--  1.3.6.1.4.1.47477.10.21.28.3.16
		-- 1.3.6.1.4.1.47477.10.21.28.3.16
		link28_ActiveSendInterval OBJECT-TYPE
			SYNTAX Integer32
			MAX-ACCESS read-write
			STATUS current
			DESCRIPTION
				"get or set the send interval of active heartbeat."
			::= { link28OBP 16 }		

--  1.3.6.1.4.1.47477.10.21.28.3.17
		-- 1.3.6.1.4.1.47477.10.21.28.3.17
		link28_ActiveTimeOut OBJECT-TYPE
			SYNTAX Integer32
			MAX-ACCESS read-write
			STATUS current
			DESCRIPTION
				"get or set how long the active heartbeat send timeout."
			::= { link28OBP 17 }

--  1.3.6.1.4.1.47477.10.21.28.3.18
		-- 1.3.6.1.4.1.47477.10.21.28.3.18
		link28_ActiveLossBypass OBJECT-TYPE
			SYNTAX Integer32
			MAX-ACCESS read-write
			STATUS current
			DESCRIPTION
				"get or set the bypass for active heartbeat packet loss."
			::= { link28OBP 18 }

--  1.3.6.1.4.1.47477.10.21.28.3.19
		-- 1.3.6.1.4.1.47477.10.21.28.3.19
		link28_PingIpAddress OBJECT-TYPE
			SYNTAX IpAddress
			MAX-ACCESS read-write
			STATUS current
			DESCRIPTION
				"get or set the ping ip address of link28."
			::= { link28OBP 19 }

--  1.3.6.1.4.1.47477.10.21.28.3.20
		-- 1.3.6.1.4.1.47477.10.21.28.3.20
		link28_PassiveHeartSwitch OBJECT-TYPE
			SYNTAX INTEGER
				{
				off(0),
				on(1)
				}
			MAX-ACCESS read-write
			STATUS current
			DESCRIPTION
				"get or set the switch status of passive heartbeat."
			::= { link28OBP 20 }
	

--  1.3.6.1.4.1.47477.10.21.28.3.21
		-- 1.3.6.1.4.1.47477.10.21.28.3.21
		link28_PassiveTimeOut OBJECT-TYPE
			SYNTAX Integer32
			MAX-ACCESS read-write
			STATUS current
			DESCRIPTION
				"get or set how long the passive heartbeat send timeout."
			::= { link28OBP 21 }

--  1.3.6.1.4.1.47477.10.21.28.3.22
		-- 1.3.6.1.4.1.47477.10.21.28.3.22
		link28_PassiveLossBypass OBJECT-TYPE
			SYNTAX Integer32
			MAX-ACCESS read-write
			STATUS current
			DESCRIPTION
				"get or set the bypass for passive heartbeat packet loss."
			::= { link28OBP 22 }

--  1.3.6.1.4.1.47477.10.21.28.3.23
		-- 1.3.6.1.4.1.47477.10.21.28.3.23
		link28_SwitchProtect OBJECT-TYPE
			SYNTAX INTEGER
				{
				off(0),
				on(1)
				}
			MAX-ACCESS read-write
			STATUS current
			DESCRIPTION
				"get or set the switch protection status of link28."
			::= { link28OBP 23 }
			
--  1.3.6.1.4.1.47477.10.21.28.3.24
		-- 1.3.6.1.4.1.47477.10.21.28.3.24
		link28_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link28OBP 24 }		

--  1.3.6.1.4.1.47477.10.21.28.3.25
		-- 1.3.6.1.4.1.47477.10.21.28.3.25
		link28_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link28OBP 25 }	

--  1.3.6.1.4.1.47477.10.21.28.3.26
		-- 1.3.6.1.4.1.47477.10.21.28.3.26
		link28_PowerAlarmStatus OBJECT-TYPE
			SYNTAX INTEGER
				{
				off(0),
				alarm(1),
				normal(2),
				na(3)
				}
			MAX-ACCESS read-only
			STATUS current
			DESCRIPTION
				"get whether a power alarm is generated."
			::= { link28OBP 26 }	


-- 1.3.6.1.4.1.47477.10.21.28.3.50.1
	link28_WorkModeChange 	OBJECT-TYPE    
    SYNTAX INTEGER	{
				manualMode(0),
				autoMode(1)
		}
	MAX-ACCESS read-only
	STATUS current
    DESCRIPTION
        "The Link mode Changed."
    ::= {link28OBPTrap 1}

-- 1.3.6.1.4.1.47477.10.21.28.3.50.2
	link28_StateChange 	OBJECT-TYPE    
    SYNTAX INTEGER	{
				bypass(0),
				primary(1)
		}
	MAX-ACCESS read-only
	STATUS current
    DESCRIPTION
        "The Link State(Channel) Changed."
    ::= {link28OBPTrap 2}

-- 1.3.6.1.4.1.47477.10.21.28.3.50.3
	link28_R1WaveSet 	OBJECT-TYPE    
    SYNTAX INTEGER	{
				w1310nm(0),
				w1550nm(1)
		}
	MAX-ACCESS read-only
	STATUS current
    DESCRIPTION
        "Set The link28 R1 Wave."
    ::= {link28OBPTrap 3}

-- 1.3.6.1.4.1.47477.10.21.28.3.50.4
	link28_R2WaveSet 	OBJECT-TYPE    
    SYNTAX INTEGER	{
				w1310nm(0),
				w1550nm(1)
		}
	MAX-ACCESS read-only
	STATUS current
    DESCRIPTION
        "Set The link28 R2 Wave."
    ::= {link28OBPTrap 4}			

-- 1.3.6.1.4.1.47477.10.21.28.3.50.5
	link28_R3WaveSet 	OBJECT-TYPE    
    SYNTAX INTEGER	{
				w1310nm(0),
				w1550nm(1)
		}
	MAX-ACCESS read-only
	STATUS current
    DESCRIPTION
        "Set The link28 R3 Wave."
    ::= {link28OBPTrap 5}

-- 1.3.6.1.4.1.47477.10.21.28.3.50.6
	link28_R4WaveSet 	OBJECT-TYPE    
    SYNTAX INTEGER	{
				w1310nm(0),
				w1550nm(1)
		}
	MAX-ACCESS read-only
	STATUS current
    DESCRIPTION
        "Set The link28 R4 Wave."
    ::= {link28OBPTrap 6}	
	
-- 1.3.6.1.4.1.47477.10.21.28.3.50.7
	link28_R1AlarmSet 	OBJECT-TYPE    
    SYNTAX DisplayString
	MAX-ACCESS read-only
	STATUS current
    DESCRIPTION
        "Set The link28 R1 Alarm Threshold."
    ::= {link28OBPTrap 7}

-- 1.3.6.1.4.1.47477.10.21.28.3.50.8
	link28_R2AlarmSet 	OBJECT-TYPE    
    SYNTAX DisplayString
	MAX-ACCESS read-only
	STATUS current
    DESCRIPTION
        "Set The link28 R2 Alarm Threshold."
    ::= {link28OBPTrap 8}
	
-- 1.3.6.1.4.1.47477.10.21.28.3.50.9
	link28_R3AlarmSet 	OBJECT-TYPE    
    SYNTAX DisplayString
	MAX-ACCESS read-only
	STATUS current
    DESCRIPTION
        "Set The link28 R3 Alarm Threshold."
    ::= {link28OBPTrap 9}

-- 1.3.6.1.4.1.47477.10.21.28.3.50.10
	link28_R4AlarmSet 	OBJECT-TYPE    
    SYNTAX DisplayString
	MAX-ACCESS read-only
	STATUS current
    DESCRIPTION
        "Set The link28 R4 Alarm Threshold."
    ::= {link28OBPTrap 10}	
	
	
-- 1.3.6.1.4.1.47477.10.21.28.3.50.11
	link28_1R1AlarmSet 	OBJECT-TYPE    
    SYNTAX DisplayString
	MAX-ACCESS read-only
	STATUS current
    DESCRIPTION
        "Set The link28 1R1 Alarm Threshold."
    ::= {link28OBPTrap 11}

-- 1.3.6.1.4.1.47477.10.21.28.3.50.12
	link28_2R1AlarmSet 	OBJECT-TYPE    
    SYNTAX DisplayString
	MAX-ACCESS read-only
	STATUS current
    DESCRIPTION
        "Set The link28 2R1 Alarm Threshold."
    ::= {link28OBPTrap 12}
	
-- 1.3.6.1.4.1.47477.10.21.28.3.50.13
	link28_1R2AlarmSet 	OBJECT-TYPE    
    SYNTAX DisplayString
	MAX-ACCESS read-only
	STATUS current
    DESCRIPTION
        "Set The link28 1R2 Alarm Threshold."
    ::= {link28OBPTrap 13}

-- 1.3.6.1.4.1.47477.10.21.28.3.50.14
	link28_2R2AlarmSet 	OBJECT-TYPE    
    SYNTAX DisplayString
	MAX-ACCESS read-only
	STATUS current
    DESCRIPTION
        "Set The link28 2R2 Alarm Threshold."
    ::= {link28OBPTrap 14}
	
-- 1.3.6.1.4.1.47477.10.21.28.3.50.15
	link28_1R3AlarmSet 	OBJECT-TYPE    
    SYNTAX DisplayString
	MAX-ACCESS read-only
	STATUS current
    DESCRIPTION
        "Set The link28 1R3 Alarm Threshold."
    ::= {link28OBPTrap 15}

-- 1.3.6.1.4.1.47477.10.21.28.3.50.16
	link28_2R3AlarmSet 	OBJECT-TYPE    
    SYNTAX DisplayString
	MAX-ACCESS read-only
	STATUS current
    DESCRIPTION
        "Set The link28 2R3 Alarm Threshold."
    ::= {link28OBPTrap 16}
	
-- 1.3.6.1.4.1.47477.10.21.28.3.50.17
	link28_1R4AlarmSet 	OBJECT-TYPE    
    SYNTAX DisplayString
	MAX-ACCESS read-only
	STATUS current
    DESCRIPTION
        "Set The link28 1R4 Alarm Threshold."
    ::= {link28OBPTrap 17}

-- 1.3.6.1.4.1.47477.10.21.28.3.50.18
	link28_2R4AlarmSet 	OBJECT-TYPE    
    SYNTAX DisplayString
	MAX-ACCESS read-only
	STATUS current
    DESCRIPTION
        "Set The link28 2R4 Alarm Threshold."
    ::= {link28OBPTrap 18}
	
-- 1.3.6.1.4.1.47477.10.21.28.3.50.19
	link28_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link28 PowerAlarmBypass2 Changed."
    ::= {link28OBPTrap 19}
	
-- 1.3.6.1.4.1.47477.10.21.28.3.50.20
	link28_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link28 PowerAlarmBypass4 Changed."
    ::= {link28OBPTrap 20}	
	
-- 1.3.6.1.4.1.47477.10.21.28.3.50.21
	link28_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link28 PowerAlarmBypass8 Changed."
    ::= {link28OBPTrap 21}
	
-- 1.3.6.1.4.1.47477.10.21.28.3.50.22
	link28_powerAlarmR1 	OBJECT-TYPE    
    SYNTAX DisplayString
	MAX-ACCESS read-only
	STATUS current
    DESCRIPTION
        "Set The link28 R1 Power Status Alarm."
    ::= {link28OBPTrap 22}
	
-- 1.3.6.1.4.1.47477.10.21.28.3.50.23
	link28_powerAlarmR2 	OBJECT-TYPE    
    SYNTAX DisplayString
	MAX-ACCESS read-only
	STATUS current
    DESCRIPTION
        "Set The link28 R2 Power Status Alarm."
    ::= {link28OBPTrap 23}
	
-- 1.3.6.1.4.1.47477.10.21.28.3.50.24
	link28_powerAlarmR3 	OBJECT-TYPE    
    SYNTAX DisplayString
	MAX-ACCESS read-only
	STATUS current
    DESCRIPTION
        "Set The link28 R3 Power Status Alarm."
    ::= {link28OBPTrap 24}
	
-- 1.3.6.1.4.1.47477.10.21.28.3.50.25
	link28_powerAlarmR4 	OBJECT-TYPE    
    SYNTAX DisplayString
	MAX-ACCESS read-only
	STATUS current
    DESCRIPTION
        "Set The link28 R4 Power Status Alarm."
    ::= {link28OBPTrap 25}
	
	
-- 1.3.6.1.4.1.47477.10.21.28.3.50.26
	link28_powerAlarm1R1 	OBJECT-TYPE    
    SYNTAX DisplayString
	MAX-ACCESS read-only
	STATUS current
    DESCRIPTION
        "Set The link28 1R1 Power Status Alarm."
    ::= {link28OBPTrap 26}
	
-- 1.3.6.1.4.1.47477.10.21.28.3.50.27
	link28_powerAlarm2R1 	OBJECT-TYPE    
    SYNTAX DisplayString
	MAX-ACCESS read-only
	STATUS current
    DESCRIPTION
        "Set The link28 2R1 Power Status Alarm."
    ::= {link28OBPTrap 27}
	
-- 1.3.6.1.4.1.47477.10.21.28.3.50.28
	link28_powerAlarm1R2 	OBJECT-TYPE    
    SYNTAX DisplayString
	MAX-ACCESS read-only
	STATUS current
    DESCRIPTION
        "Set The link28 1R2 Power Status Alarm."
    ::= {link28OBPTrap 28}
	
-- 1.3.6.1.4.1.47477.10.21.28.3.50.29
	link28_powerAlarm2R2 	OBJECT-TYPE    
    SYNTAX DisplayString
	MAX-ACCESS read-only
	STATUS current
    DESCRIPTION
        "Set The link28 2R2 Power Status Alarm."
    ::= {link28OBPTrap 29}
	
-- 1.3.6.1.4.1.47477.10.21.28.3.50.30
	link28_powerAlarm1R3 	OBJECT-TYPE    
    SYNTAX DisplayString
	MAX-ACCESS read-only
	STATUS current
    DESCRIPTION
        "Set The link28 1R3 Power Status Alarm."
    ::= {link28OBPTrap 30}
	
-- 1.3.6.1.4.1.47477.10.21.28.3.50.31
	link28_powerAlarm2R3 	OBJECT-TYPE    
    SYNTAX DisplayString
	MAX-ACCESS read-only
	STATUS current
    DESCRIPTION
        "Set The link28 2R1 Power Status Alarm."
    ::= {link28OBPTrap 31}
	
-- 1.3.6.1.4.1.47477.10.21.28.3.50.32
	link28_powerAlarm1R4 	OBJECT-TYPE    
    SYNTAX DisplayString
	MAX-ACCESS read-only
	STATUS current
    DESCRIPTION
        "Set The link28 1R4 Power Status Alarm."
    ::= {link28OBPTrap 32}
	
-- 1.3.6.1.4.1.47477.10.21.28.3.50.33
	link28_powerAlarm2R4 	OBJECT-TYPE    
    SYNTAX DisplayString
	MAX-ACCESS read-only
	STATUS current
    DESCRIPTION
        "Set The link28 2R4 Power Status Alarm."
    ::= {link28OBPTrap 33}
	
--  1.3.6.1.4.1.47477.10.21.29.3.1
		-- 1.3.6.1.4.1.47477.10.21.29.3.1
		link29_State OBJECT-TYPE
			SYNTAX INTEGER
				{
				off(0),
				on(1)
				}
			MAX-ACCESS read-only
			STATUS current
			DESCRIPTION
				"get the information about whether link29 is working."
			::= { link29OBP 1 }

		
--  1.3.6.1.4.1.47477.10.21.29.3.2
		-- 1.3.6.1.4.1.47477.10.21.29.3.2
		link29_DeviceType OBJECT-TYPE
			SYNTAX DisplayString
			MAX-ACCESS read-only
			STATUS current
			DESCRIPTION
				"get the type of card in link29."
			::= { link29OBP 2 }

			
--  1.3.6.1.4.1.47477.10.21.29.3.3
		-- 1.3.6.1.4.1.47477.10.21.29.3.3
		link29_WorkMode OBJECT-TYPE
			SYNTAX INTEGER
				{
				manualMode(0),
				autoMode(1)
				}
			MAX-ACCESS read-write
			STATUS current
			DESCRIPTION
				"get or set link29's work mode."
			::= { link29OBP 3 }

		
--  1.3.6.1.4.1.47477.10.21.29.3.4
		-- 1.3.6.1.4.1.47477.10.21.29.3.4
		link29_Channel OBJECT-TYPE
			SYNTAX INTEGER
				{
				bypass(0),
				primary(1)
				}
			MAX-ACCESS read-write
			STATUS current
			DESCRIPTION
				"get or set the channel in which link29 works."
			::= { link29OBP 4 }


--  1.3.6.1.4.1.47477.10.21.29.3.5
		-- 1.3.6.1.4.1.47477.10.21.29.3.5
		link29_R1Power OBJECT-TYPE
			SYNTAX DisplayString
			MAX-ACCESS read-only
			STATUS current
			DESCRIPTION
				"get the power of R1 in link29."
			::= { link29OBP 5 }

		
--  1.3.6.1.4.1.47477.10.21.29.3.6
		-- 1.3.6.1.4.1.47477.10.21.29.3.6
		link29_R2Power OBJECT-TYPE
			SYNTAX DisplayString
			MAX-ACCESS read-only
			STATUS current
			DESCRIPTION
				"get the power of R2 in link29."
			::= { link29OBP 6 }
			
--  1.3.6.1.4.1.47477.10.21.29.3.35
		-- 1.3.6.1.4.1.47477.10.21.29.3.35
		link29_R3Power OBJECT-TYPE
			SYNTAX DisplayString
			MAX-ACCESS read-only
			STATUS current
			DESCRIPTION
				"get the power of R3 in link29."
			::= { link29OBP 35 }
			
--  1.3.6.1.4.1.47477.10.21.29.3.36
		-- 1.3.6.1.4.1.47477.10.21.29.3.36
		link29_R4Power OBJECT-TYPE
			SYNTAX DisplayString
			MAX-ACCESS read-only
			STATUS current
			DESCRIPTION
				"get the power of R4 in link29."
			::= { link29OBP 36 }		
		
--  1.3.6.1.4.1.47477.10.21.29.3.7
		-- 1.3.6.1.4.1.47477.10.21.29.3.7
		link29_R1Wave OBJECT-TYPE
			SYNTAX INTEGER
				{
				w1310nm(0),
				w1550nm(1),
				na(2)
				}
			MAX-ACCESS read-write
			STATUS current
			DESCRIPTION
				"get or set the wave length of R1 in link29."
			::= { link29OBP 7 }

		
--  1.3.6.1.4.1.47477.10.21.29.3.8
		-- 1.3.6.1.4.1.47477.10.21.29.3.8
		link29_R2Wave OBJECT-TYPE
			SYNTAX INTEGER
				{
				w1310nm(0),
				w1550nm(1),
				na(2)
				}
			MAX-ACCESS read-write
			STATUS current
			DESCRIPTION
				"get or set the wave length of R2 in link29."
			::= { link29OBP 8 }


--  1.3.6.1.4.1.47477.10.21.29.3.27
		-- 1.3.6.1.4.1.47477.10.21.29.3.27
		link29_R3Wave OBJECT-TYPE
			SYNTAX INTEGER
				{
				w1310nm(0),
				w1550nm(1),
				na(2)
				}
			MAX-ACCESS read-write
			STATUS current
			DESCRIPTION
				"get or set the wave length of R3 in link29."
			::= { link29OBP 27 }

		
--  1.3.6.1.4.1.47477.10.21.29.3.28
		-- 1.3.6.1.4.1.47477.10.21.29.3.28
		link29_R4Wave OBJECT-TYPE
			SYNTAX INTEGER
				{
				w1310nm(0),
				w1550nm(1),
				na(2)
				}
			MAX-ACCESS read-write
			STATUS current
			DESCRIPTION
				"get or set the wave length of R4 in link29."
			::= { link29OBP 28 }
			
--  1.3.6.1.4.1.47477.10.21.29.3.9
		-- 1.3.6.1.4.1.47477.10.21.29.3.9
		link29_R1AlarmPower OBJECT-TYPE
			SYNTAX DisplayString
			MAX-ACCESS read-write
			STATUS current
			DESCRIPTION
				"get or set the power alarm threshold of R1 in link29."
			::= { link29OBP 9 }

		
--  1.3.6.1.4.1.47477.10.21.29.3.10
		-- 1.3.6.1.4.1.47477.10.21.29.3.10
		link29_R2AlarmPower OBJECT-TYPE
			SYNTAX DisplayString
			MAX-ACCESS read-write
			STATUS current
			DESCRIPTION
				"get or set the power alarm threshold of R2 in link29."
			::= { link29OBP 10 }


--  1.3.6.1.4.1.47477.10.21.29.3.29
		-- 1.3.6.1.4.1.47477.10.21.29.3.29
		link29_R3AlarmPower OBJECT-TYPE
			SYNTAX DisplayString
			MAX-ACCESS read-write
			STATUS current
			DESCRIPTION
				"get or set the power alarm threshold of R3 in link29."
			::= { link29OBP 29 }

		
--  1.3.6.1.4.1.47477.10.21.29.3.30
		-- 1.3.6.1.4.1.47477.10.21.29.3.30
		link29_R4AlarmPower OBJECT-TYPE
			SYNTAX DisplayString
			MAX-ACCESS read-write
			STATUS current
			DESCRIPTION
				"get or set the power alarm threshold of R4 in link29."
			::= { link29OBP 30 }

-- OBP4
--  1.3.6.1.4.1.47477.10.21.29.3.37
		-- 1.3.6.1.4.1.47477.10.21.29.3.37
		link29_1R1Power OBJECT-TYPE
			SYNTAX DisplayString
			MAX-ACCESS read-only
			STATUS current
			DESCRIPTION
				"get the power of 1R1 in link29."
			::= { link29OBP 37 }
			
--  1.3.6.1.4.1.47477.10.21.29.3.38
		-- 1.3.6.1.4.1.47477.10.21.29.3.38
		link29_1R2Power OBJECT-TYPE
			SYNTAX DisplayString
			MAX-ACCESS read-only
			STATUS current
			DESCRIPTION
				"get the power of 1R2 in link29."
			::= { link29OBP 38 }

--  1.3.6.1.4.1.47477.10.21.29.3.39
		-- 1.3.6.1.4.1.47477.10.21.29.3.39
		link29_1R3Power OBJECT-TYPE
			SYNTAX DisplayString
			MAX-ACCESS read-only
			STATUS current
			DESCRIPTION
				"get the power of 1R3 in link29."
			::= { link29OBP 39 }
			
--  1.3.6.1.4.1.47477.10.21.29.3.40
		-- 1.3.6.1.4.1.47477.10.21.29.3.40
		link29_1R4Power OBJECT-TYPE
			SYNTAX DisplayString
			MAX-ACCESS read-only
			STATUS current
			DESCRIPTION
				"get the power of 1R4 in link29."
			::= { link29OBP 40 }

--  1.3.6.1.4.1.47477.10.21.29.3.41
		-- 1.3.6.1.4.1.47477.10.21.29.3.41
		link29_2R1Power OBJECT-TYPE
			SYNTAX DisplayString
			MAX-ACCESS read-only
			STATUS current
			DESCRIPTION
				"get the power of 2R1 in link29."
			::= { link29OBP 41 }
			
--  1.3.6.1.4.1.47477.10.21.29.3.42
		-- 1.3.6.1.4.1.47477.10.21.29.3.42
		link29_2R2Power OBJECT-TYPE
			SYNTAX DisplayString
			MAX-ACCESS read-only
			STATUS current
			DESCRIPTION
				"get the power of 2R2 in link29."
			::= { link29OBP 42 }

--  1.3.6.1.4.1.47477.10.21.29.3.41
		-- 1.3.6.1.4.1.47477.10.21.29.3.43
		link29_2R3Power OBJECT-TYPE
			SYNTAX DisplayString
			MAX-ACCESS read-only
			STATUS current
			DESCRIPTION
				"get the power of 2R3 in link29."
			::= { link29OBP 43 }
			
--  1.3.6.1.4.1.47477.10.21.29.3.42
		-- 1.3.6.1.4.1.47477.10.21.29.3.44
		link29_2R4Power OBJECT-TYPE
			SYNTAX DisplayString
			MAX-ACCESS read-only
			STATUS current
			DESCRIPTION
				"get the power of 2R4 in link29."
			::= { link29OBP 44 }
			
--  1.3.6.1.4.1.47477.10.21.29.3.49
		-- 1.3.6.1.4.1.47477.10.21.29.3.49
		link29_1R1Wave OBJECT-TYPE
			SYNTAX INTEGER
				{
				w850nm(0),
				na(2)
				}
			MAX-ACCESS read-only
			STATUS current
			DESCRIPTION
				"get the wave length of 1R1 in link29."
			::= { link29OBP 49 }
		
--  1.3.6.1.4.1.47477.10.21.29.3.60
		-- 1.3.6.1.4.1.47477.10.21.29.3.60
		link29_1R2Wave OBJECT-TYPE
			SYNTAX INTEGER
				{
				w850nm(0),
				na(2)
				}
			MAX-ACCESS read-only
			STATUS current
			DESCRIPTION
				"get the wave length of 1R2 in link29."
			::= { link29OBP 60 }

--  1.3.6.1.4.1.47477.10.21.29.3.61
		-- 1.3.6.1.4.1.47477.10.21.29.3.61
		link29_1R3Wave OBJECT-TYPE
			SYNTAX INTEGER
				{
				w850nm(0),
				na(2)
				}
			MAX-ACCESS read-only
			STATUS current
			DESCRIPTION
				"get the wave length of 1R3 in link29."
			::= { link29OBP 61 }

		
--  1.3.6.1.4.1.47477.10.21.29.3.62
		-- 1.3.6.1.4.1.47477.10.21.29.3.62
		link29_1R4Wave OBJECT-TYPE
			SYNTAX INTEGER
				{
				w850nm(0),
				na(2)
				}
			MAX-ACCESS read-only
			STATUS current
			DESCRIPTION
				"get the wave length of 1R4 in link29."
			::= { link29OBP 62 }
	
--  1.3.6.1.4.1.47477.10.21.29.3.63
		-- 1.3.6.1.4.1.47477.10.21.29.3.63
		link29_2R1Wave OBJECT-TYPE
			SYNTAX INTEGER
				{
				w850nm(0),
				na(2)
				}
			MAX-ACCESS read-only
			STATUS current
			DESCRIPTION
				"get the wave length of 2R1 in link29."
			::= { link29OBP 63 }

		
--  1.3.6.1.4.1.47477.10.21.29.3.64
		-- 1.3.6.1.4.1.47477.10.21.29.3.64
		link29_2R2Wave OBJECT-TYPE
			SYNTAX INTEGER
				{
				w850nm(0),
				na(2)
				}
			MAX-ACCESS read-only
			STATUS current
			DESCRIPTION
				"get the wave length of 2R2 in link29."
			::= { link29OBP 64 }	
	
--  1.3.6.1.4.1.47477.10.21.29.3.65
		-- 1.3.6.1.4.1.47477.10.21.29.3.65
		link29_2R3Wave OBJECT-TYPE
			SYNTAX INTEGER
				{
				w850nm(0),
				na(2)
				}
			MAX-ACCESS read-only
			STATUS current
			DESCRIPTION
				"get the wave length of 2R3 in link29."
			::= { link29OBP 65 }

		
--  1.3.6.1.4.1.47477.10.21.29.3.66
		-- 1.3.6.1.4.1.47477.10.21.29.3.66
		link29_2R4Wave OBJECT-TYPE
			SYNTAX INTEGER
				{
				w850nm(0),
				na(2)
				}
			MAX-ACCESS read-only
			STATUS current
			DESCRIPTION
				"get the wave length of 2R4 in link29."
			::= { link29OBP 66 }	
			
--  1.3.6.1.4.1.47477.10.21.29.3.31
		-- 1.3.6.1.4.1.47477.10.21.29.3.31
		link29_1R1AlarmPower OBJECT-TYPE
			SYNTAX DisplayString
			MAX-ACCESS read-write
			STATUS current
			DESCRIPTION
				"get or set the power alarm threshold of 1R1 in link29."
			::= { link29OBP 31 }
			
--  1.3.6.1.4.1.47477.10.21.29.3.32
		-- 1.3.6.1.4.1.47477.10.21.29.3.32
		link29_1R2AlarmPower OBJECT-TYPE
			SYNTAX DisplayString
			MAX-ACCESS read-write
			STATUS current
			DESCRIPTION
				"get or set the power alarm threshold of 1R2 in link29."
			::= { link29OBP 32 }

--  1.3.6.1.4.1.47477.10.21.29.3.33
		-- 1.3.6.1.4.1.47477.10.21.29.3.33
		link29_1R3AlarmPower OBJECT-TYPE
			SYNTAX DisplayString
			MAX-ACCESS read-write
			STATUS current
			DESCRIPTION
				"get or set the power alarm threshold of 1R3 in link29."
			::= { link29OBP 33 }
			
--  1.3.6.1.4.1.47477.10.21.29.3.34
		-- 1.3.6.1.4.1.47477.10.21.29.3.34
		link29_1R4AlarmPower OBJECT-TYPE
			SYNTAX DisplayString
			MAX-ACCESS read-write
			STATUS current
			DESCRIPTION
				"get or set the power alarm threshold of 1R4 in link29."
			::= { link29OBP 34 }

--  1.3.6.1.4.1.47477.10.21.29.3.45
		-- 1.3.6.1.4.1.47477.10.21.29.3.45
		link29_2R1AlarmPower OBJECT-TYPE
			SYNTAX DisplayString
			MAX-ACCESS read-write
			STATUS current
			DESCRIPTION
				"get or set the power alarm threshold of 2R1 in link29."
			::= { link29OBP 45 }
			
--  1.3.6.1.4.1.47477.10.21.29.3.46
		-- 1.3.6.1.4.1.47477.10.21.29.3.46
		link29_2R2AlarmPower OBJECT-TYPE
			SYNTAX DisplayString
			MAX-ACCESS read-write
			STATUS current
			DESCRIPTION
				"get or set the power alarm threshold of 2R2 in link29."
			::= { link29OBP 46 }

--  1.3.6.1.4.1.47477.10.21.29.3.47
		-- 1.3.6.1.4.1.47477.10.21.29.3.47
		link29_2R3AlarmPower OBJECT-TYPE
			SYNTAX DisplayString
			MAX-ACCESS read-write
			STATUS current
			DESCRIPTION
				"get or set the power alarm threshold of 2R3 in link29."
			::= { link29OBP 47 }
			
--  1.3.6.1.4.1.47477.10.21.29.3.48
		-- 1.3.6.1.4.1.47477.10.21.29.3.48
		link29_2R4AlarmPower OBJECT-TYPE
			SYNTAX DisplayString
			MAX-ACCESS read-write
			STATUS current
			DESCRIPTION
				"get or set the power alarm threshold of 2R4 in link29."
			::= { link29OBP 48 }
			
--  1.3.6.1.4.1.47477.10.21.29.3.11
		-- 1.3.6.1.4.1.47477.10.21.29.3.11
		link29_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link29OBP 11 }
			
--  1.3.6.1.4.1.47477.10.21.29.3.67
		-- 1.3.6.1.4.1.47477.10.21.29.3.67
		link29_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link29OBP 67 }
			
--  1.3.6.1.4.1.47477.10.21.29.3.68
		-- 1.3.6.1.4.1.47477.10.21.29.3.68
		link29_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link29OBP 68 }
			
--  1.3.6.1.4.1.47477.10.21.29.3.12
		-- 1.3.6.1.4.1.47477.10.21.29.3.12
		link29_ReturnDelay OBJECT-TYPE
			--SYNTAX Integer32
			SYNTAX Integer32
			MAX-ACCESS read-write
			STATUS current
			DESCRIPTION
				"get or set how long link29 takes to return to automatic mode."
			::= { link29OBP 12 }
			
--  1.3.6.1.4.1.47477.10.21.29.3.13
		-- 1.3.6.1.4.1.47477.10.21.29.3.13
		link29_BackMode OBJECT-TYPE
			SYNTAX INTEGER
				{
				autoNoBack(0),
				autoBack(1)
				}
			MAX-ACCESS read-write
			STATUS current
			DESCRIPTION
				"get or set the back mode of link29."
			::= { link29OBP 13 }

		
--  1.3.6.1.4.1.47477.10.21.29.3.14
		-- 1.3.6.1.4.1.47477.10.21.29.3.14
		link29_BackDelay OBJECT-TYPE
			SYNTAX Integer32
			MAX-ACCESS read-write
			STATUS current
			DESCRIPTION
				"get or set the back delay."
			::= { link29OBP 14 }

--  1.3.6.1.4.1.47477.10.21.29.3.15
		-- 1.3.6.1.4.1.47477.10.21.29.3.15
		link29_ActiveHeartSwitch OBJECT-TYPE
			SYNTAX INTEGER
				{
				off(0),
				on(1)
				}
			MAX-ACCESS read-write
			STATUS current
			DESCRIPTION
				"get or set the switch status of active heartbeat."
			::= { link29OBP 15 }

		
--  1.3.6.1.4.1.47477.10.21.29.3.16
		-- 1.3.6.1.4.1.47477.10.21.29.3.16
		link29_ActiveSendInterval OBJECT-TYPE
			SYNTAX Integer32
			MAX-ACCESS read-write
			STATUS current
			DESCRIPTION
				"get or set the send interval of active heartbeat."
			::= { link29OBP 16 }		

--  1.3.6.1.4.1.47477.10.21.29.3.17
		-- 1.3.6.1.4.1.47477.10.21.29.3.17
		link29_ActiveTimeOut OBJECT-TYPE
			SYNTAX Integer32
			MAX-ACCESS read-write
			STATUS current
			DESCRIPTION
				"get or set how long the active heartbeat send timeout."
			::= { link29OBP 17 }

--  1.3.6.1.4.1.47477.10.21.29.3.18
		-- 1.3.6.1.4.1.47477.10.21.29.3.18
		link29_ActiveLossBypass OBJECT-TYPE
			SYNTAX Integer32
			MAX-ACCESS read-write
			STATUS current
			DESCRIPTION
				"get or set the bypass for active heartbeat packet loss."
			::= { link29OBP 18 }

--  1.3.6.1.4.1.47477.10.21.29.3.19
		-- 1.3.6.1.4.1.47477.10.21.29.3.19
		link29_PingIpAddress OBJECT-TYPE
			SYNTAX IpAddress
			MAX-ACCESS read-write
			STATUS current
			DESCRIPTION
				"get or set the ping ip address of link29."
			::= { link29OBP 19 }

--  1.3.6.1.4.1.47477.10.21.29.3.20
		-- 1.3.6.1.4.1.47477.10.21.29.3.20
		link29_PassiveHeartSwitch OBJECT-TYPE
			SYNTAX INTEGER
				{
				off(0),
				on(1)
				}
			MAX-ACCESS read-write
			STATUS current
			DESCRIPTION
				"get or set the switch status of passive heartbeat."
			::= { link29OBP 20 }
	

--  1.3.6.1.4.1.47477.10.21.29.3.21
		-- 1.3.6.1.4.1.47477.10.21.29.3.21
		link29_PassiveTimeOut OBJECT-TYPE
			SYNTAX Integer32
			MAX-ACCESS read-write
			STATUS current
			DESCRIPTION
				"get or set how long the passive heartbeat send timeout."
			::= { link29OBP 21 }

--  1.3.6.1.4.1.47477.10.21.29.3.22
		-- 1.3.6.1.4.1.47477.10.21.29.3.22
		link29_PassiveLossBypass OBJECT-TYPE
			SYNTAX Integer32
			MAX-ACCESS read-write
			STATUS current
			DESCRIPTION
				"get or set the bypass for passive heartbeat packet loss."
			::= { link29OBP 22 }

--  1.3.6.1.4.1.47477.10.21.29.3.23
		-- 1.3.6.1.4.1.47477.10.21.29.3.23
		link29_SwitchProtect OBJECT-TYPE
			SYNTAX INTEGER
				{
				off(0),
				on(1)
				}
			MAX-ACCESS read-write
			STATUS current
			DESCRIPTION
				"get or set the switch protection status of link29."
			::= { link29OBP 23 }
			
--  1.3.6.1.4.1.47477.10.21.29.3.24
		-- 1.3.6.1.4.1.47477.10.21.29.3.24
		link29_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link29OBP 24 }		

--  1.3.6.1.4.1.47477.10.21.29.3.25
		-- 1.3.6.1.4.1.47477.10.21.29.3.25
		link29_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link29OBP 25 }	

--  1.3.6.1.4.1.47477.10.21.29.3.26
		-- 1.3.6.1.4.1.47477.10.21.29.3.26
		link29_PowerAlarmStatus OBJECT-TYPE
			SYNTAX INTEGER
				{
				off(0),
				alarm(1),
				normal(2),
				na(3)
				}
			MAX-ACCESS read-only
			STATUS current
			DESCRIPTION
				"get whether a power alarm is generated."
			::= { link29OBP 26 }	


-- 1.3.6.1.4.1.47477.10.21.29.3.50.1
	link29_WorkModeChange 	OBJECT-TYPE    
    SYNTAX INTEGER	{
				manualMode(0),
				autoMode(1)
		}
	MAX-ACCESS read-only
	STATUS current
    DESCRIPTION
        "The Link mode Changed."
    ::= {link29OBPTrap 1}

-- 1.3.6.1.4.1.47477.10.21.29.3.50.2
	link29_StateChange 	OBJECT-TYPE    
    SYNTAX INTEGER	{
				bypass(0),
				primary(1)
		}
	MAX-ACCESS read-only
	STATUS current
    DESCRIPTION
        "The Link State(Channel) Changed."
    ::= {link29OBPTrap 2}

-- 1.3.6.1.4.1.47477.10.21.29.3.50.3
	link29_R1WaveSet 	OBJECT-TYPE    
    SYNTAX INTEGER	{
				w1310nm(0),
				w1550nm(1)
		}
	MAX-ACCESS read-only
	STATUS current
    DESCRIPTION
        "Set The link29 R1 Wave."
    ::= {link29OBPTrap 3}

-- 1.3.6.1.4.1.47477.10.21.29.3.50.4
	link29_R2WaveSet 	OBJECT-TYPE    
    SYNTAX INTEGER	{
				w1310nm(0),
				w1550nm(1)
		}
	MAX-ACCESS read-only
	STATUS current
    DESCRIPTION
        "Set The link29 R2 Wave."
    ::= {link29OBPTrap 4}			

-- 1.3.6.1.4.1.47477.10.21.29.3.50.5
	link29_R3WaveSet 	OBJECT-TYPE    
    SYNTAX INTEGER	{
				w1310nm(0),
				w1550nm(1)
		}
	MAX-ACCESS read-only
	STATUS current
    DESCRIPTION
        "Set The link29 R3 Wave."
    ::= {link29OBPTrap 5}

-- 1.3.6.1.4.1.47477.10.21.29.3.50.6
	link29_R4WaveSet 	OBJECT-TYPE    
    SYNTAX INTEGER	{
				w1310nm(0),
				w1550nm(1)
		}
	MAX-ACCESS read-only
	STATUS current
    DESCRIPTION
        "Set The link29 R4 Wave."
    ::= {link29OBPTrap 6}	
	
-- 1.3.6.1.4.1.47477.10.21.29.3.50.7
	link29_R1AlarmSet 	OBJECT-TYPE    
    SYNTAX DisplayString
	MAX-ACCESS read-only
	STATUS current
    DESCRIPTION
        "Set The link29 R1 Alarm Threshold."
    ::= {link29OBPTrap 7}

-- 1.3.6.1.4.1.47477.10.21.29.3.50.8
	link29_R2AlarmSet 	OBJECT-TYPE    
    SYNTAX DisplayString
	MAX-ACCESS read-only
	STATUS current
    DESCRIPTION
        "Set The link29 R2 Alarm Threshold."
    ::= {link29OBPTrap 8}
	
-- 1.3.6.1.4.1.47477.10.21.29.3.50.9
	link29_R3AlarmSet 	OBJECT-TYPE    
    SYNTAX DisplayString
	MAX-ACCESS read-only
	STATUS current
    DESCRIPTION
        "Set The link29 R3 Alarm Threshold."
    ::= {link29OBPTrap 9}

-- 1.3.6.1.4.1.47477.10.21.29.3.50.10
	link29_R4AlarmSet 	OBJECT-TYPE    
    SYNTAX DisplayString
	MAX-ACCESS read-only
	STATUS current
    DESCRIPTION
        "Set The link29 R4 Alarm Threshold."
    ::= {link29OBPTrap 10}	
	
	
-- 1.3.6.1.4.1.47477.10.21.29.3.50.11
	link29_1R1AlarmSet 	OBJECT-TYPE    
    SYNTAX DisplayString
	MAX-ACCESS read-only
	STATUS current
    DESCRIPTION
        "Set The link29 1R1 Alarm Threshold."
    ::= {link29OBPTrap 11}

-- 1.3.6.1.4.1.47477.10.21.29.3.50.12
	link29_2R1AlarmSet 	OBJECT-TYPE    
    SYNTAX DisplayString
	MAX-ACCESS read-only
	STATUS current
    DESCRIPTION
        "Set The link29 2R1 Alarm Threshold."
    ::= {link29OBPTrap 12}
	
-- 1.3.6.1.4.1.47477.10.21.29.3.50.13
	link29_1R2AlarmSet 	OBJECT-TYPE    
    SYNTAX DisplayString
	MAX-ACCESS read-only
	STATUS current
    DESCRIPTION
        "Set The link29 1R2 Alarm Threshold."
    ::= {link29OBPTrap 13}

-- 1.3.6.1.4.1.47477.10.21.29.3.50.14
	link29_2R2AlarmSet 	OBJECT-TYPE    
    SYNTAX DisplayString
	MAX-ACCESS read-only
	STATUS current
    DESCRIPTION
        "Set The link29 2R2 Alarm Threshold."
    ::= {link29OBPTrap 14}
	
-- 1.3.6.1.4.1.47477.10.21.29.3.50.15
	link29_1R3AlarmSet 	OBJECT-TYPE    
    SYNTAX DisplayString
	MAX-ACCESS read-only
	STATUS current
    DESCRIPTION
        "Set The link29 1R3 Alarm Threshold."
    ::= {link29OBPTrap 15}

-- 1.3.6.1.4.1.47477.10.21.29.3.50.16
	link29_2R3AlarmSet 	OBJECT-TYPE    
    SYNTAX DisplayString
	MAX-ACCESS read-only
	STATUS current
    DESCRIPTION
        "Set The link29 2R3 Alarm Threshold."
    ::= {link29OBPTrap 16}
	
-- 1.3.6.1.4.1.47477.10.21.29.3.50.17
	link29_1R4AlarmSet 	OBJECT-TYPE    
    SYNTAX DisplayString
	MAX-ACCESS read-only
	STATUS current
    DESCRIPTION
        "Set The link29 1R4 Alarm Threshold."
    ::= {link29OBPTrap 17}

-- 1.3.6.1.4.1.47477.10.21.29.3.50.18
	link29_2R4AlarmSet 	OBJECT-TYPE    
    SYNTAX DisplayString
	MAX-ACCESS read-only
	STATUS current
    DESCRIPTION
        "Set The link29 2R4 Alarm Threshold."
    ::= {link29OBPTrap 18}
	
-- 1.3.6.1.4.1.47477.10.21.29.3.50.19
	link29_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link29 PowerAlarmBypass2 Changed."
    ::= {link29OBPTrap 19}
	
-- 1.3.6.1.4.1.47477.10.21.29.3.50.20
	link29_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link29 PowerAlarmBypass4 Changed."
    ::= {link29OBPTrap 20}	
	
-- 1.3.6.1.4.1.47477.10.21.29.3.50.21
	link29_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link29 PowerAlarmBypass8 Changed."
    ::= {link29OBPTrap 21}
	
-- 1.3.6.1.4.1.47477.10.21.29.3.50.22
	link29_powerAlarmR1 	OBJECT-TYPE    
    SYNTAX DisplayString
	MAX-ACCESS read-only
	STATUS current
    DESCRIPTION
        "Set The link29 R1 Power Status Alarm."
    ::= {link29OBPTrap 22}
	
-- 1.3.6.1.4.1.47477.10.21.29.3.50.23
	link29_powerAlarmR2 	OBJECT-TYPE    
    SYNTAX DisplayString
	MAX-ACCESS read-only
	STATUS current
    DESCRIPTION
        "Set The link29 R2 Power Status Alarm."
    ::= {link29OBPTrap 23}
	
-- 1.3.6.1.4.1.47477.10.21.29.3.50.24
	link29_powerAlarmR3 	OBJECT-TYPE    
    SYNTAX DisplayString
	MAX-ACCESS read-only
	STATUS current
    DESCRIPTION
        "Set The link29 R3 Power Status Alarm."
    ::= {link29OBPTrap 24}
	
-- 1.3.6.1.4.1.47477.10.21.29.3.50.25
	link29_powerAlarmR4 	OBJECT-TYPE    
    SYNTAX DisplayString
	MAX-ACCESS read-only
	STATUS current
    DESCRIPTION
        "Set The link29 R4 Power Status Alarm."
    ::= {link29OBPTrap 25}
	
	
-- 1.3.6.1.4.1.47477.10.21.29.3.50.26
	link29_powerAlarm1R1 	OBJECT-TYPE    
    SYNTAX DisplayString
	MAX-ACCESS read-only
	STATUS current
    DESCRIPTION
        "Set The link29 1R1 Power Status Alarm."
    ::= {link29OBPTrap 26}
	
-- 1.3.6.1.4.1.47477.10.21.29.3.50.27
	link29_powerAlarm2R1 	OBJECT-TYPE    
    SYNTAX DisplayString
	MAX-ACCESS read-only
	STATUS current
    DESCRIPTION
        "Set The link29 2R1 Power Status Alarm."
    ::= {link29OBPTrap 27}
	
-- 1.3.6.1.4.1.47477.10.21.29.3.50.28
	link29_powerAlarm1R2 	OBJECT-TYPE    
    SYNTAX DisplayString
	MAX-ACCESS read-only
	STATUS current
    DESCRIPTION
        "Set The link29 1R2 Power Status Alarm."
    ::= {link29OBPTrap 28}
	
-- 1.3.6.1.4.1.47477.10.21.29.3.50.29
	link29_powerAlarm2R2 	OBJECT-TYPE    
    SYNTAX DisplayString
	MAX-ACCESS read-only
	STATUS current
    DESCRIPTION
        "Set The link29 2R2 Power Status Alarm."
    ::= {link29OBPTrap 29}
	
-- 1.3.6.1.4.1.47477.10.21.29.3.50.30
	link29_powerAlarm1R3 	OBJECT-TYPE    
    SYNTAX DisplayString
	MAX-ACCESS read-only
	STATUS current
    DESCRIPTION
        "Set The link29 1R3 Power Status Alarm."
    ::= {link29OBPTrap 30}
	
-- 1.3.6.1.4.1.47477.10.21.29.3.50.31
	link29_powerAlarm2R3 	OBJECT-TYPE    
    SYNTAX DisplayString
	MAX-ACCESS read-only
	STATUS current
    DESCRIPTION
        "Set The link29 2R1 Power Status Alarm."
    ::= {link29OBPTrap 31}
	
-- 1.3.6.1.4.1.47477.10.21.29.3.50.32
	link29_powerAlarm1R4 	OBJECT-TYPE    
    SYNTAX DisplayString
	MAX-ACCESS read-only
	STATUS current
    DESCRIPTION
        "Set The link29 1R4 Power Status Alarm."
    ::= {link29OBPTrap 32}
	
-- 1.3.6.1.4.1.47477.10.21.29.3.50.33
	link29_powerAlarm2R4 	OBJECT-TYPE    
    SYNTAX DisplayString
	MAX-ACCESS read-only
	STATUS current
    DESCRIPTION
        "Set The link29 2R4 Power Status Alarm."
    ::= {link29OBPTrap 33}
	
--  1.3.6.1.4.1.47477.10.21.30.3.1
		-- 1.3.6.1.4.1.47477.10.21.30.3.1
		link30_State OBJECT-TYPE
			SYNTAX INTEGER
				{
				off(0),
				on(1)
				}
			MAX-ACCESS read-only
			STATUS current
			DESCRIPTION
				"get the information about whether link30 is working."
			::= { link30OBP 1 }

		
--  1.3.6.1.4.1.47477.10.21.30.3.2
		-- 1.3.6.1.4.1.47477.10.21.30.3.2
		link30_DeviceType OBJECT-TYPE
			SYNTAX DisplayString
			MAX-ACCESS read-only
			STATUS current
			DESCRIPTION
				"get the type of card in link30."
			::= { link30OBP 2 }

			
--  1.3.6.1.4.1.47477.10.21.30.3.3
		-- 1.3.6.1.4.1.47477.10.21.30.3.3
		link30_WorkMode OBJECT-TYPE
			SYNTAX INTEGER
				{
				manualMode(0),
				autoMode(1)
				}
			MAX-ACCESS read-write
			STATUS current
			DESCRIPTION
				"get or set link30's work mode."
			::= { link30OBP 3 }

		
--  1.3.6.1.4.1.47477.10.21.30.3.4
		-- 1.3.6.1.4.1.47477.10.21.30.3.4
		link30_Channel OBJECT-TYPE
			SYNTAX INTEGER
				{
				bypass(0),
				primary(1)
				}
			MAX-ACCESS read-write
			STATUS current
			DESCRIPTION
				"get or set the channel in which link30 works."
			::= { link30OBP 4 }


--  1.3.6.1.4.1.47477.10.21.30.3.5
		-- 1.3.6.1.4.1.47477.10.21.30.3.5
		link30_R1Power OBJECT-TYPE
			SYNTAX DisplayString
			MAX-ACCESS read-only
			STATUS current
			DESCRIPTION
				"get the power of R1 in link30."
			::= { link30OBP 5 }

		
--  1.3.6.1.4.1.47477.10.21.30.3.6
		-- 1.3.6.1.4.1.47477.10.21.30.3.6
		link30_R2Power OBJECT-TYPE
			SYNTAX DisplayString
			MAX-ACCESS read-only
			STATUS current
			DESCRIPTION
				"get the power of R2 in link30."
			::= { link30OBP 6 }
			
--  1.3.6.1.4.1.47477.10.21.30.3.35
		-- 1.3.6.1.4.1.47477.10.21.30.3.35
		link30_R3Power OBJECT-TYPE
			SYNTAX DisplayString
			MAX-ACCESS read-only
			STATUS current
			DESCRIPTION
				"get the power of R3 in link30."
			::= { link30OBP 35 }
			
--  1.3.6.1.4.1.47477.10.21.30.3.36
		-- 1.3.6.1.4.1.47477.10.21.30.3.36
		link30_R4Power OBJECT-TYPE
			SYNTAX DisplayString
			MAX-ACCESS read-only
			STATUS current
			DESCRIPTION
				"get the power of R4 in link30."
			::= { link30OBP 36 }		
		
--  1.3.6.1.4.1.47477.10.21.30.3.7
		-- 1.3.6.1.4.1.47477.10.21.30.3.7
		link30_R1Wave OBJECT-TYPE
			SYNTAX INTEGER
				{
				w1310nm(0),
				w1550nm(1),
				na(2)
				}
			MAX-ACCESS read-write
			STATUS current
			DESCRIPTION
				"get or set the wave length of R1 in link30."
			::= { link30OBP 7 }

		
--  1.3.6.1.4.1.47477.10.21.30.3.8
		-- 1.3.6.1.4.1.47477.10.21.30.3.8
		link30_R2Wave OBJECT-TYPE
			SYNTAX INTEGER
				{
				w1310nm(0),
				w1550nm(1),
				na(2)
				}
			MAX-ACCESS read-write
			STATUS current
			DESCRIPTION
				"get or set the wave length of R2 in link30."
			::= { link30OBP 8 }


--  1.3.6.1.4.1.47477.10.21.30.3.27
		-- 1.3.6.1.4.1.47477.10.21.30.3.27
		link30_R3Wave OBJECT-TYPE
			SYNTAX INTEGER
				{
				w1310nm(0),
				w1550nm(1),
				na(2)
				}
			MAX-ACCESS read-write
			STATUS current
			DESCRIPTION
				"get or set the wave length of R3 in link30."
			::= { link30OBP 27 }

		
--  1.3.6.1.4.1.47477.10.21.30.3.28
		-- 1.3.6.1.4.1.47477.10.21.30.3.28
		link30_R4Wave OBJECT-TYPE
			SYNTAX INTEGER
				{
				w1310nm(0),
				w1550nm(1),
				na(2)
				}
			MAX-ACCESS read-write
			STATUS current
			DESCRIPTION
				"get or set the wave length of R4 in link30."
			::= { link30OBP 28 }
			
--  1.3.6.1.4.1.47477.10.21.30.3.9
		-- 1.3.6.1.4.1.47477.10.21.30.3.9
		link30_R1AlarmPower OBJECT-TYPE
			SYNTAX DisplayString
			MAX-ACCESS read-write
			STATUS current
			DESCRIPTION
				"get or set the power alarm threshold of R1 in link30."
			::= { link30OBP 9 }

		
--  1.3.6.1.4.1.47477.10.21.30.3.10
		-- 1.3.6.1.4.1.47477.10.21.30.3.10
		link30_R2AlarmPower OBJECT-TYPE
			SYNTAX DisplayString
			MAX-ACCESS read-write
			STATUS current
			DESCRIPTION
				"get or set the power alarm threshold of R2 in link30."
			::= { link30OBP 10 }


--  1.3.6.1.4.1.47477.10.21.30.3.29
		-- 1.3.6.1.4.1.47477.10.21.30.3.29
		link30_R3AlarmPower OBJECT-TYPE
			SYNTAX DisplayString
			MAX-ACCESS read-write
			STATUS current
			DESCRIPTION
				"get or set the power alarm threshold of R3 in link30."
			::= { link30OBP 29 }

		
--  1.3.6.1.4.1.47477.10.21.30.3.30
		-- 1.3.6.1.4.1.47477.10.21.30.3.30
		link30_R4AlarmPower OBJECT-TYPE
			SYNTAX DisplayString
			MAX-ACCESS read-write
			STATUS current
			DESCRIPTION
				"get or set the power alarm threshold of R4 in link30."
			::= { link30OBP 30 }

-- OBP4
--  1.3.6.1.4.1.47477.10.21.30.3.37
		-- 1.3.6.1.4.1.47477.10.21.30.3.37
		link30_1R1Power OBJECT-TYPE
			SYNTAX DisplayString
			MAX-ACCESS read-only
			STATUS current
			DESCRIPTION
				"get the power of 1R1 in link30."
			::= { link30OBP 37 }
			
--  1.3.6.1.4.1.47477.10.21.30.3.38
		-- 1.3.6.1.4.1.47477.10.21.30.3.38
		link30_1R2Power OBJECT-TYPE
			SYNTAX DisplayString
			MAX-ACCESS read-only
			STATUS current
			DESCRIPTION
				"get the power of 1R2 in link30."
			::= { link30OBP 38 }

--  1.3.6.1.4.1.47477.10.21.30.3.39
		-- 1.3.6.1.4.1.47477.10.21.30.3.39
		link30_1R3Power OBJECT-TYPE
			SYNTAX DisplayString
			MAX-ACCESS read-only
			STATUS current
			DESCRIPTION
				"get the power of 1R3 in link30."
			::= { link30OBP 39 }
			
--  1.3.6.1.4.1.47477.10.21.30.3.40
		-- 1.3.6.1.4.1.47477.10.21.30.3.40
		link30_1R4Power OBJECT-TYPE
			SYNTAX DisplayString
			MAX-ACCESS read-only
			STATUS current
			DESCRIPTION
				"get the power of 1R4 in link30."
			::= { link30OBP 40 }

--  1.3.6.1.4.1.47477.10.21.30.3.41
		-- 1.3.6.1.4.1.47477.10.21.30.3.41
		link30_2R1Power OBJECT-TYPE
			SYNTAX DisplayString
			MAX-ACCESS read-only
			STATUS current
			DESCRIPTION
				"get the power of 2R1 in link30."
			::= { link30OBP 41 }
			
--  1.3.6.1.4.1.47477.10.21.30.3.42
		-- 1.3.6.1.4.1.47477.10.21.30.3.42
		link30_2R2Power OBJECT-TYPE
			SYNTAX DisplayString
			MAX-ACCESS read-only
			STATUS current
			DESCRIPTION
				"get the power of 2R2 in link30."
			::= { link30OBP 42 }

--  1.3.6.1.4.1.47477.10.21.30.3.41
		-- 1.3.6.1.4.1.47477.10.21.30.3.43
		link30_2R3Power OBJECT-TYPE
			SYNTAX DisplayString
			MAX-ACCESS read-only
			STATUS current
			DESCRIPTION
				"get the power of 2R3 in link30."
			::= { link30OBP 43 }
			
--  1.3.6.1.4.1.47477.10.21.30.3.42
		-- 1.3.6.1.4.1.47477.10.21.30.3.44
		link30_2R4Power OBJECT-TYPE
			SYNTAX DisplayString
			MAX-ACCESS read-only
			STATUS current
			DESCRIPTION
				"get the power of 2R4 in link30."
			::= { link30OBP 44 }
			
--  1.3.6.1.4.1.47477.10.21.30.3.49
		-- 1.3.6.1.4.1.47477.10.21.30.3.49
		link30_1R1Wave OBJECT-TYPE
			SYNTAX INTEGER
				{
				w850nm(0),
				na(2)
				}
			MAX-ACCESS read-only
			STATUS current
			DESCRIPTION
				"get the wave length of 1R1 in link30."
			::= { link30OBP 49 }
		
--  1.3.6.1.4.1.47477.10.21.30.3.60
		-- 1.3.6.1.4.1.47477.10.21.30.3.60
		link30_1R2Wave OBJECT-TYPE
			SYNTAX INTEGER
				{
				w850nm(0),
				na(2)
				}
			MAX-ACCESS read-only
			STATUS current
			DESCRIPTION
				"get the wave length of 1R2 in link30."
			::= { link30OBP 60 }

--  1.3.6.1.4.1.47477.10.21.30.3.61
		-- 1.3.6.1.4.1.47477.10.21.30.3.61
		link30_1R3Wave OBJECT-TYPE
			SYNTAX INTEGER
				{
				w850nm(0),
				na(2)
				}
			MAX-ACCESS read-only
			STATUS current
			DESCRIPTION
				"get the wave length of 1R3 in link30."
			::= { link30OBP 61 }

		
--  1.3.6.1.4.1.47477.10.21.30.3.62
		-- 1.3.6.1.4.1.47477.10.21.30.3.62
		link30_1R4Wave OBJECT-TYPE
			SYNTAX INTEGER
				{
				w850nm(0),
				na(2)
				}
			MAX-ACCESS read-only
			STATUS current
			DESCRIPTION
				"get the wave length of 1R4 in link30."
			::= { link30OBP 62 }
	
--  1.3.6.1.4.1.47477.10.21.30.3.63
		-- 1.3.6.1.4.1.47477.10.21.30.3.63
		link30_2R1Wave OBJECT-TYPE
			SYNTAX INTEGER
				{
				w850nm(0),
				na(2)
				}
			MAX-ACCESS read-only
			STATUS current
			DESCRIPTION
				"get the wave length of 2R1 in link30."
			::= { link30OBP 63 }

		
--  1.3.6.1.4.1.47477.10.21.30.3.64
		-- 1.3.6.1.4.1.47477.10.21.30.3.64
		link30_2R2Wave OBJECT-TYPE
			SYNTAX INTEGER
				{
				w850nm(0),
				na(2)
				}
			MAX-ACCESS read-only
			STATUS current
			DESCRIPTION
				"get the wave length of 2R2 in link30."
			::= { link30OBP 64 }	
	
--  1.3.6.1.4.1.47477.10.21.30.3.65
		-- 1.3.6.1.4.1.47477.10.21.30.3.65
		link30_2R3Wave OBJECT-TYPE
			SYNTAX INTEGER
				{
				w850nm(0),
				na(2)
				}
			MAX-ACCESS read-only
			STATUS current
			DESCRIPTION
				"get the wave length of 2R3 in link30."
			::= { link30OBP 65 }

		
--  1.3.6.1.4.1.47477.10.21.30.3.66
		-- 1.3.6.1.4.1.47477.10.21.30.3.66
		link30_2R4Wave OBJECT-TYPE
			SYNTAX INTEGER
				{
				w850nm(0),
				na(2)
				}
			MAX-ACCESS read-only
			STATUS current
			DESCRIPTION
				"get the wave length of 2R4 in link30."
			::= { link30OBP 66 }	
			
--  1.3.6.1.4.1.47477.10.21.30.3.31
		-- 1.3.6.1.4.1.47477.10.21.30.3.31
		link30_1R1AlarmPower OBJECT-TYPE
			SYNTAX DisplayString
			MAX-ACCESS read-write
			STATUS current
			DESCRIPTION
				"get or set the power alarm threshold of 1R1 in link30."
			::= { link30OBP 31 }
			
--  1.3.6.1.4.1.47477.10.21.30.3.32
		-- 1.3.6.1.4.1.47477.10.21.30.3.32
		link30_1R2AlarmPower OBJECT-TYPE
			SYNTAX DisplayString
			MAX-ACCESS read-write
			STATUS current
			DESCRIPTION
				"get or set the power alarm threshold of 1R2 in link30."
			::= { link30OBP 32 }

--  1.3.6.1.4.1.47477.10.21.30.3.33
		-- 1.3.6.1.4.1.47477.10.21.30.3.33
		link30_1R3AlarmPower OBJECT-TYPE
			SYNTAX DisplayString
			MAX-ACCESS read-write
			STATUS current
			DESCRIPTION
				"get or set the power alarm threshold of 1R3 in link30."
			::= { link30OBP 33 }
			
--  1.3.6.1.4.1.47477.10.21.30.3.34
		-- 1.3.6.1.4.1.47477.10.21.30.3.34
		link30_1R4AlarmPower OBJECT-TYPE
			SYNTAX DisplayString
			MAX-ACCESS read-write
			STATUS current
			DESCRIPTION
				"get or set the power alarm threshold of 1R4 in link30."
			::= { link30OBP 34 }

--  1.3.6.1.4.1.47477.10.21.30.3.45
		-- 1.3.6.1.4.1.47477.10.21.30.3.45
		link30_2R1AlarmPower OBJECT-TYPE
			SYNTAX DisplayString
			MAX-ACCESS read-write
			STATUS current
			DESCRIPTION
				"get or set the power alarm threshold of 2R1 in link30."
			::= { link30OBP 45 }
			
--  1.3.6.1.4.1.47477.10.21.30.3.46
		-- 1.3.6.1.4.1.47477.10.21.30.3.46
		link30_2R2AlarmPower OBJECT-TYPE
			SYNTAX DisplayString
			MAX-ACCESS read-write
			STATUS current
			DESCRIPTION
				"get or set the power alarm threshold of 2R2 in link30."
			::= { link30OBP 46 }

--  1.3.6.1.4.1.47477.10.21.30.3.47
		-- 1.3.6.1.4.1.47477.10.21.30.3.47
		link30_2R3AlarmPower OBJECT-TYPE
			SYNTAX DisplayString
			MAX-ACCESS read-write
			STATUS current
			DESCRIPTION
				"get or set the power alarm threshold of 2R3 in link30."
			::= { link30OBP 47 }
			
--  1.3.6.1.4.1.47477.10.21.30.3.48
		-- 1.3.6.1.4.1.47477.10.21.30.3.48
		link30_2R4AlarmPower OBJECT-TYPE
			SYNTAX DisplayString
			MAX-ACCESS read-write
			STATUS current
			DESCRIPTION
				"get or set the power alarm threshold of 2R4 in link30."
			::= { link30OBP 48 }
			
--  1.3.6.1.4.1.47477.10.21.30.3.11
		-- 1.3.6.1.4.1.47477.10.21.30.3.11
		link30_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link30OBP 11 }
			
--  1.3.6.1.4.1.47477.10.21.30.3.67
		-- 1.3.6.1.4.1.47477.10.21.30.3.67
		link30_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link30OBP 67 }
			
--  1.3.6.1.4.1.47477.10.21.30.3.68
		-- 1.3.6.1.4.1.47477.10.21.30.3.68
		link30_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link30OBP 68 }
			
--  1.3.6.1.4.1.47477.10.21.30.3.12
		-- 1.3.6.1.4.1.47477.10.21.30.3.12
		link30_ReturnDelay OBJECT-TYPE
			--SYNTAX Integer32
			SYNTAX Integer32
			MAX-ACCESS read-write
			STATUS current
			DESCRIPTION
				"get or set how long link30 takes to return to automatic mode."
			::= { link30OBP 12 }
			
--  1.3.6.1.4.1.47477.10.21.30.3.13
		-- 1.3.6.1.4.1.47477.10.21.30.3.13
		link30_BackMode OBJECT-TYPE
			SYNTAX INTEGER
				{
				autoNoBack(0),
				autoBack(1)
				}
			MAX-ACCESS read-write
			STATUS current
			DESCRIPTION
				"get or set the back mode of link30."
			::= { link30OBP 13 }

		
--  1.3.6.1.4.1.47477.10.21.30.3.14
		-- 1.3.6.1.4.1.47477.10.21.30.3.14
		link30_BackDelay OBJECT-TYPE
			SYNTAX Integer32
			MAX-ACCESS read-write
			STATUS current
			DESCRIPTION
				"get or set the back delay."
			::= { link30OBP 14 }

--  1.3.6.1.4.1.47477.10.21.30.3.15
		-- 1.3.6.1.4.1.47477.10.21.30.3.15
		link30_ActiveHeartSwitch OBJECT-TYPE
			SYNTAX INTEGER
				{
				off(0),
				on(1)
				}
			MAX-ACCESS read-write
			STATUS current
			DESCRIPTION
				"get or set the switch status of active heartbeat."
			::= { link30OBP 15 }

		
--  1.3.6.1.4.1.47477.10.21.30.3.16
		-- 1.3.6.1.4.1.47477.10.21.30.3.16
		link30_ActiveSendInterval OBJECT-TYPE
			SYNTAX Integer32
			MAX-ACCESS read-write
			STATUS current
			DESCRIPTION
				"get or set the send interval of active heartbeat."
			::= { link30OBP 16 }		

--  1.3.6.1.4.1.47477.10.21.30.3.17
		-- 1.3.6.1.4.1.47477.10.21.30.3.17
		link30_ActiveTimeOut OBJECT-TYPE
			SYNTAX Integer32
			MAX-ACCESS read-write
			STATUS current
			DESCRIPTION
				"get or set how long the active heartbeat send timeout."
			::= { link30OBP 17 }

--  1.3.6.1.4.1.47477.10.21.30.3.18
		-- 1.3.6.1.4.1.47477.10.21.30.3.18
		link30_ActiveLossBypass OBJECT-TYPE
			SYNTAX Integer32
			MAX-ACCESS read-write
			STATUS current
			DESCRIPTION
				"get or set the bypass for active heartbeat packet loss."
			::= { link30OBP 18 }

--  1.3.6.1.4.1.47477.10.21.30.3.19
		-- 1.3.6.1.4.1.47477.10.21.30.3.19
		link30_PingIpAddress OBJECT-TYPE
			SYNTAX IpAddress
			MAX-ACCESS read-write
			STATUS current
			DESCRIPTION
				"get or set the ping ip address of link30."
			::= { link30OBP 19 }

--  1.3.6.1.4.1.47477.10.21.30.3.20
		-- 1.3.6.1.4.1.47477.10.21.30.3.20
		link30_PassiveHeartSwitch OBJECT-TYPE
			SYNTAX INTEGER
				{
				off(0),
				on(1)
				}
			MAX-ACCESS read-write
			STATUS current
			DESCRIPTION
				"get or set the switch status of passive heartbeat."
			::= { link30OBP 20 }
	

--  1.3.6.1.4.1.47477.10.21.30.3.21
		-- 1.3.6.1.4.1.47477.10.21.30.3.21
		link30_PassiveTimeOut OBJECT-TYPE
			SYNTAX Integer32
			MAX-ACCESS read-write
			STATUS current
			DESCRIPTION
				"get or set how long the passive heartbeat send timeout."
			::= { link30OBP 21 }

--  1.3.6.1.4.1.47477.10.21.30.3.22
		-- 1.3.6.1.4.1.47477.10.21.30.3.22
		link30_PassiveLossBypass OBJECT-TYPE
			SYNTAX Integer32
			MAX-ACCESS read-write
			STATUS current
			DESCRIPTION
				"get or set the bypass for passive heartbeat packet loss."
			::= { link30OBP 22 }

--  1.3.6.1.4.1.47477.10.21.30.3.23
		-- 1.3.6.1.4.1.47477.10.21.30.3.23
		link30_SwitchProtect OBJECT-TYPE
			SYNTAX INTEGER
				{
				off(0),
				on(1)
				}
			MAX-ACCESS read-write
			STATUS current
			DESCRIPTION
				"get or set the switch protection status of link30."
			::= { link30OBP 23 }
			
--  1.3.6.1.4.1.47477.10.21.30.3.24
		-- 1.3.6.1.4.1.47477.10.21.30.3.24
		link30_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link30OBP 24 }		

--  1.3.6.1.4.1.47477.10.21.30.3.25
		-- 1.3.6.1.4.1.47477.10.21.30.3.25
		link30_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link30OBP 25 }	

--  1.3.6.1.4.1.47477.10.21.30.3.26
		-- 1.3.6.1.4.1.47477.10.21.30.3.26
		link30_PowerAlarmStatus OBJECT-TYPE
			SYNTAX INTEGER
				{
				off(0),
				alarm(1),
				normal(2),
				na(3)
				}
			MAX-ACCESS read-only
			STATUS current
			DESCRIPTION
				"get whether a power alarm is generated."
			::= { link30OBP 26 }	


-- 1.3.6.1.4.1.47477.10.21.30.3.50.1
	link30_WorkModeChange 	OBJECT-TYPE    
    SYNTAX INTEGER	{
				manualMode(0),
				autoMode(1)
		}
	MAX-ACCESS read-only
	STATUS current
    DESCRIPTION
        "The Link mode Changed."
    ::= {link30OBPTrap 1}

-- 1.3.6.1.4.1.47477.10.21.30.3.50.2
	link30_StateChange 	OBJECT-TYPE    
    SYNTAX INTEGER	{
				bypass(0),
				primary(1)
		}
	MAX-ACCESS read-only
	STATUS current
    DESCRIPTION
        "The Link State(Channel) Changed."
    ::= {link30OBPTrap 2}

-- 1.3.6.1.4.1.47477.10.21.30.3.50.3
	link30_R1WaveSet 	OBJECT-TYPE    
    SYNTAX INTEGER	{
				w1310nm(0),
				w1550nm(1)
		}
	MAX-ACCESS read-only
	STATUS current
    DESCRIPTION
        "Set The link30 R1 Wave."
    ::= {link30OBPTrap 3}

-- 1.3.6.1.4.1.47477.10.21.30.3.50.4
	link30_R2WaveSet 	OBJECT-TYPE    
    SYNTAX INTEGER	{
				w1310nm(0),
				w1550nm(1)
		}
	MAX-ACCESS read-only
	STATUS current
    DESCRIPTION
        "Set The link30 R2 Wave."
    ::= {link30OBPTrap 4}			

-- 1.3.6.1.4.1.47477.10.21.30.3.50.5
	link30_R3WaveSet 	OBJECT-TYPE    
    SYNTAX INTEGER	{
				w1310nm(0),
				w1550nm(1)
		}
	MAX-ACCESS read-only
	STATUS current
    DESCRIPTION
        "Set The link30 R3 Wave."
    ::= {link30OBPTrap 5}

-- 1.3.6.1.4.1.47477.10.21.30.3.50.6
	link30_R4WaveSet 	OBJECT-TYPE    
    SYNTAX INTEGER	{
				w1310nm(0),
				w1550nm(1)
		}
	MAX-ACCESS read-only
	STATUS current
    DESCRIPTION
        "Set The link30 R4 Wave."
    ::= {link30OBPTrap 6}	
	
-- 1.3.6.1.4.1.47477.10.21.30.3.50.7
	link30_R1AlarmSet 	OBJECT-TYPE    
    SYNTAX DisplayString
	MAX-ACCESS read-only
	STATUS current
    DESCRIPTION
        "Set The link30 R1 Alarm Threshold."
    ::= {link30OBPTrap 7}

-- 1.3.6.1.4.1.47477.10.21.30.3.50.8
	link30_R2AlarmSet 	OBJECT-TYPE    
    SYNTAX DisplayString
	MAX-ACCESS read-only
	STATUS current
    DESCRIPTION
        "Set The link30 R2 Alarm Threshold."
    ::= {link30OBPTrap 8}
	
-- 1.3.6.1.4.1.47477.10.21.30.3.50.9
	link30_R3AlarmSet 	OBJECT-TYPE    
    SYNTAX DisplayString
	MAX-ACCESS read-only
	STATUS current
    DESCRIPTION
        "Set The link30 R3 Alarm Threshold."
    ::= {link30OBPTrap 9}

-- 1.3.6.1.4.1.47477.10.21.30.3.50.10
	link30_R4AlarmSet 	OBJECT-TYPE    
    SYNTAX DisplayString
	MAX-ACCESS read-only
	STATUS current
    DESCRIPTION
        "Set The link30 R4 Alarm Threshold."
    ::= {link30OBPTrap 10}	
	
	
-- 1.3.6.1.4.1.47477.10.21.30.3.50.11
	link30_1R1AlarmSet 	OBJECT-TYPE    
    SYNTAX DisplayString
	MAX-ACCESS read-only
	STATUS current
    DESCRIPTION
        "Set The link30 1R1 Alarm Threshold."
    ::= {link30OBPTrap 11}

-- 1.3.6.1.4.1.47477.10.21.30.3.50.12
	link30_2R1AlarmSet 	OBJECT-TYPE    
    SYNTAX DisplayString
	MAX-ACCESS read-only
	STATUS current
    DESCRIPTION
        "Set The link30 2R1 Alarm Threshold."
    ::= {link30OBPTrap 12}
	
-- 1.3.6.1.4.1.47477.10.21.30.3.50.13
	link30_1R2AlarmSet 	OBJECT-TYPE    
    SYNTAX DisplayString
	MAX-ACCESS read-only
	STATUS current
    DESCRIPTION
        "Set The link30 1R2 Alarm Threshold."
    ::= {link30OBPTrap 13}

-- 1.3.6.1.4.1.47477.10.21.30.3.50.14
	link30_2R2AlarmSet 	OBJECT-TYPE    
    SYNTAX DisplayString
	MAX-ACCESS read-only
	STATUS current
    DESCRIPTION
        "Set The link30 2R2 Alarm Threshold."
    ::= {link30OBPTrap 14}
	
-- 1.3.6.1.4.1.47477.10.21.30.3.50.15
	link30_1R3AlarmSet 	OBJECT-TYPE    
    SYNTAX DisplayString
	MAX-ACCESS read-only
	STATUS current
    DESCRIPTION
        "Set The link30 1R3 Alarm Threshold."
    ::= {link30OBPTrap 15}

-- 1.3.6.1.4.1.47477.10.21.30.3.50.16
	link30_2R3AlarmSet 	OBJECT-TYPE    
    SYNTAX DisplayString
	MAX-ACCESS read-only
	STATUS current
    DESCRIPTION
        "Set The link30 2R3 Alarm Threshold."
    ::= {link30OBPTrap 16}
	
-- 1.3.6.1.4.1.47477.10.21.30.3.50.17
	link30_1R4AlarmSet 	OBJECT-TYPE    
    SYNTAX DisplayString
	MAX-ACCESS read-only
	STATUS current
    DESCRIPTION
        "Set The link30 1R4 Alarm Threshold."
    ::= {link30OBPTrap 17}

-- 1.3.6.1.4.1.47477.10.21.30.3.50.18
	link30_2R4AlarmSet 	OBJECT-TYPE    
    SYNTAX DisplayString
	MAX-ACCESS read-only
	STATUS current
    DESCRIPTION
        "Set The link30 2R4 Alarm Threshold."
    ::= {link30OBPTrap 18}
	
-- 1.3.6.1.4.1.47477.10.21.30.3.50.19
	link30_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link30 PowerAlarmBypass2 Changed."
    ::= {link30OBPTrap 19}
	
-- 1.3.6.1.4.1.47477.10.21.30.3.50.20
	link30_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link30 PowerAlarmBypass4 Changed."
    ::= {link30OBPTrap 20}	
	
-- 1.3.6.1.4.1.47477.10.21.30.3.50.21
	link30_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link30 PowerAlarmBypass8 Changed."
    ::= {link30OBPTrap 21}
	
-- 1.3.6.1.4.1.47477.10.21.30.3.50.22
	link30_powerAlarmR1 	OBJECT-TYPE    
    SYNTAX DisplayString
	MAX-ACCESS read-only
	STATUS current
    DESCRIPTION
        "Set The link30 R1 Power Status Alarm."
    ::= {link30OBPTrap 22}
	
-- 1.3.6.1.4.1.47477.10.21.30.3.50.23
	link30_powerAlarmR2 	OBJECT-TYPE    
    SYNTAX DisplayString
	MAX-ACCESS read-only
	STATUS current
    DESCRIPTION
        "Set The link30 R2 Power Status Alarm."
    ::= {link30OBPTrap 23}
	
-- 1.3.6.1.4.1.47477.10.21.30.3.50.24
	link30_powerAlarmR3 	OBJECT-TYPE    
    SYNTAX DisplayString
	MAX-ACCESS read-only
	STATUS current
    DESCRIPTION
        "Set The link30 R3 Power Status Alarm."
    ::= {link30OBPTrap 24}
	
-- 1.3.6.1.4.1.47477.10.21.30.3.50.25
	link30_powerAlarmR4 	OBJECT-TYPE    
    SYNTAX DisplayString
	MAX-ACCESS read-only
	STATUS current
    DESCRIPTION
        "Set The link30 R4 Power Status Alarm."
    ::= {link30OBPTrap 25}
	
	
-- 1.3.6.1.4.1.47477.10.21.30.3.50.26
	link30_powerAlarm1R1 	OBJECT-TYPE    
    SYNTAX DisplayString
	MAX-ACCESS read-only
	STATUS current
    DESCRIPTION
        "Set The link30 1R1 Power Status Alarm."
    ::= {link30OBPTrap 26}
	
-- 1.3.6.1.4.1.47477.10.21.30.3.50.27
	link30_powerAlarm2R1 	OBJECT-TYPE    
    SYNTAX DisplayString
	MAX-ACCESS read-only
	STATUS current
    DESCRIPTION
        "Set The link30 2R1 Power Status Alarm."
    ::= {link30OBPTrap 27}
	
-- 1.3.6.1.4.1.47477.10.21.30.3.50.28
	link30_powerAlarm1R2 	OBJECT-TYPE    
    SYNTAX DisplayString
	MAX-ACCESS read-only
	STATUS current
    DESCRIPTION
        "Set The link30 1R2 Power Status Alarm."
    ::= {link30OBPTrap 28}
	
-- 1.3.6.1.4.1.47477.10.21.30.3.50.29
	link30_powerAlarm2R2 	OBJECT-TYPE    
    SYNTAX DisplayString
	MAX-ACCESS read-only
	STATUS current
    DESCRIPTION
        "Set The link30 2R2 Power Status Alarm."
    ::= {link30OBPTrap 29}
	
-- 1.3.6.1.4.1.47477.10.21.30.3.50.30
	link30_powerAlarm1R3 	OBJECT-TYPE    
    SYNTAX DisplayString
	MAX-ACCESS read-only
	STATUS current
    DESCRIPTION
        "Set The link30 1R3 Power Status Alarm."
    ::= {link30OBPTrap 30}
	
-- 1.3.6.1.4.1.47477.10.21.30.3.50.31
	link30_powerAlarm2R3 	OBJECT-TYPE    
    SYNTAX DisplayString
	MAX-ACCESS read-only
	STATUS current
    DESCRIPTION
        "Set The link30 2R1 Power Status Alarm."
    ::= {link30OBPTrap 31}
	
-- 1.3.6.1.4.1.47477.10.21.30.3.50.32
	link30_powerAlarm1R4 	OBJECT-TYPE    
    SYNTAX DisplayString
	MAX-ACCESS read-only
	STATUS current
    DESCRIPTION
        "Set The link30 1R4 Power Status Alarm."
    ::= {link30OBPTrap 32}
	
-- 1.3.6.1.4.1.47477.10.21.30.3.50.33
	link30_powerAlarm2R4 	OBJECT-TYPE    
    SYNTAX DisplayString
	MAX-ACCESS read-only
	STATUS current
    DESCRIPTION
        "Set The link30 2R4 Power Status Alarm."
    ::= {link30OBPTrap 33}
	
--  1.3.6.1.4.1.47477.10.21.31.3.1
		-- 1.3.6.1.4.1.47477.10.21.31.3.1
		link31_State OBJECT-TYPE
			SYNTAX INTEGER
				{
				off(0),
				on(1)
				}
			MAX-ACCESS read-only
			STATUS current
			DESCRIPTION
				"get the information about whether link31 is working."
			::= { link31OBP 1 }

		
--  1.3.6.1.4.1.47477.10.21.31.3.2
		-- 1.3.6.1.4.1.47477.10.21.31.3.2
		link31_DeviceType OBJECT-TYPE
			SYNTAX DisplayString
			MAX-ACCESS read-only
			STATUS current
			DESCRIPTION
				"get the type of card in link31."
			::= { link31OBP 2 }

			
--  1.3.6.1.4.1.47477.10.21.31.3.3
		-- 1.3.6.1.4.1.47477.10.21.31.3.3
		link31_WorkMode OBJECT-TYPE
			SYNTAX INTEGER
				{
				manualMode(0),
				autoMode(1)
				}
			MAX-ACCESS read-write
			STATUS current
			DESCRIPTION
				"get or set link31's work mode."
			::= { link31OBP 3 }

		
--  1.3.6.1.4.1.47477.10.21.31.3.4
		-- 1.3.6.1.4.1.47477.10.21.31.3.4
		link31_Channel OBJECT-TYPE
			SYNTAX INTEGER
				{
				bypass(0),
				primary(1)
				}
			MAX-ACCESS read-write
			STATUS current
			DESCRIPTION
				"get or set the channel in which link31 works."
			::= { link31OBP 4 }


--  1.3.6.1.4.1.47477.10.21.31.3.5
		-- 1.3.6.1.4.1.47477.10.21.31.3.5
		link31_R1Power OBJECT-TYPE
			SYNTAX DisplayString
			MAX-ACCESS read-only
			STATUS current
			DESCRIPTION
				"get the power of R1 in link31."
			::= { link31OBP 5 }

		
--  1.3.6.1.4.1.47477.10.21.31.3.6
		-- 1.3.6.1.4.1.47477.10.21.31.3.6
		link31_R2Power OBJECT-TYPE
			SYNTAX DisplayString
			MAX-ACCESS read-only
			STATUS current
			DESCRIPTION
				"get the power of R2 in link31."
			::= { link31OBP 6 }
			
--  1.3.6.1.4.1.47477.10.21.31.3.35
		-- 1.3.6.1.4.1.47477.10.21.31.3.35
		link31_R3Power OBJECT-TYPE
			SYNTAX DisplayString
			MAX-ACCESS read-only
			STATUS current
			DESCRIPTION
				"get the power of R3 in link31."
			::= { link31OBP 35 }
			
--  1.3.6.1.4.1.47477.10.21.31.3.36
		-- 1.3.6.1.4.1.47477.10.21.31.3.36
		link31_R4Power OBJECT-TYPE
			SYNTAX DisplayString
			MAX-ACCESS read-only
			STATUS current
			DESCRIPTION
				"get the power of R4 in link31."
			::= { link31OBP 36 }		
		
--  1.3.6.1.4.1.47477.10.21.31.3.7
		-- 1.3.6.1.4.1.47477.10.21.31.3.7
		link31_R1Wave OBJECT-TYPE
			SYNTAX INTEGER
				{
				w1310nm(0),
				w1550nm(1),
				na(2)
				}
			MAX-ACCESS read-write
			STATUS current
			DESCRIPTION
				"get or set the wave length of R1 in link31."
			::= { link31OBP 7 }

		
--  1.3.6.1.4.1.47477.10.21.31.3.8
		-- 1.3.6.1.4.1.47477.10.21.31.3.8
		link31_R2Wave OBJECT-TYPE
			SYNTAX INTEGER
				{
				w1310nm(0),
				w1550nm(1),
				na(2)
				}
			MAX-ACCESS read-write
			STATUS current
			DESCRIPTION
				"get or set the wave length of R2 in link31."
			::= { link31OBP 8 }


--  1.3.6.1.4.1.47477.10.21.31.3.27
		-- 1.3.6.1.4.1.47477.10.21.31.3.27
		link31_R3Wave OBJECT-TYPE
			SYNTAX INTEGER
				{
				w1310nm(0),
				w1550nm(1),
				na(2)
				}
			MAX-ACCESS read-write
			STATUS current
			DESCRIPTION
				"get or set the wave length of R3 in link31."
			::= { link31OBP 27 }

		
--  1.3.6.1.4.1.47477.10.21.31.3.28
		-- 1.3.6.1.4.1.47477.10.21.31.3.28
		link31_R4Wave OBJECT-TYPE
			SYNTAX INTEGER
				{
				w1310nm(0),
				w1550nm(1),
				na(2)
				}
			MAX-ACCESS read-write
			STATUS current
			DESCRIPTION
				"get or set the wave length of R4 in link31."
			::= { link31OBP 28 }
			
--  1.3.6.1.4.1.47477.10.21.31.3.9
		-- 1.3.6.1.4.1.47477.10.21.31.3.9
		link31_R1AlarmPower OBJECT-TYPE
			SYNTAX DisplayString
			MAX-ACCESS read-write
			STATUS current
			DESCRIPTION
				"get or set the power alarm threshold of R1 in link31."
			::= { link31OBP 9 }

		
--  1.3.6.1.4.1.47477.10.21.31.3.10
		-- 1.3.6.1.4.1.47477.10.21.31.3.10
		link31_R2AlarmPower OBJECT-TYPE
			SYNTAX DisplayString
			MAX-ACCESS read-write
			STATUS current
			DESCRIPTION
				"get or set the power alarm threshold of R2 in link31."
			::= { link31OBP 10 }


--  1.3.6.1.4.1.47477.10.21.31.3.29
		-- 1.3.6.1.4.1.47477.10.21.31.3.29
		link31_R3AlarmPower OBJECT-TYPE
			SYNTAX DisplayString
			MAX-ACCESS read-write
			STATUS current
			DESCRIPTION
				"get or set the power alarm threshold of R3 in link31."
			::= { link31OBP 29 }

		
--  1.3.6.1.4.1.47477.10.21.31.3.30
		-- 1.3.6.1.4.1.47477.10.21.31.3.30
		link31_R4AlarmPower OBJECT-TYPE
			SYNTAX DisplayString
			MAX-ACCESS read-write
			STATUS current
			DESCRIPTION
				"get or set the power alarm threshold of R4 in link31."
			::= { link31OBP 30 }

-- OBP4
--  1.3.6.1.4.1.47477.10.21.31.3.37
		-- 1.3.6.1.4.1.47477.10.21.31.3.37
		link31_1R1Power OBJECT-TYPE
			SYNTAX DisplayString
			MAX-ACCESS read-only
			STATUS current
			DESCRIPTION
				"get the power of 1R1 in link31."
			::= { link31OBP 37 }
			
--  1.3.6.1.4.1.47477.10.21.31.3.38
		-- 1.3.6.1.4.1.47477.10.21.31.3.38
		link31_1R2Power OBJECT-TYPE
			SYNTAX DisplayString
			MAX-ACCESS read-only
			STATUS current
			DESCRIPTION
				"get the power of 1R2 in link31."
			::= { link31OBP 38 }

--  1.3.6.1.4.1.47477.10.21.31.3.39
		-- 1.3.6.1.4.1.47477.10.21.31.3.39
		link31_1R3Power OBJECT-TYPE
			SYNTAX DisplayString
			MAX-ACCESS read-only
			STATUS current
			DESCRIPTION
				"get the power of 1R3 in link31."
			::= { link31OBP 39 }
			
--  1.3.6.1.4.1.47477.10.21.31.3.40
		-- 1.3.6.1.4.1.47477.10.21.31.3.40
		link31_1R4Power OBJECT-TYPE
			SYNTAX DisplayString
			MAX-ACCESS read-only
			STATUS current
			DESCRIPTION
				"get the power of 1R4 in link31."
			::= { link31OBP 40 }

--  1.3.6.1.4.1.47477.10.21.31.3.41
		-- 1.3.6.1.4.1.47477.10.21.31.3.41
		link31_2R1Power OBJECT-TYPE
			SYNTAX DisplayString
			MAX-ACCESS read-only
			STATUS current
			DESCRIPTION
				"get the power of 2R1 in link31."
			::= { link31OBP 41 }
			
--  1.3.6.1.4.1.47477.10.21.31.3.42
		-- 1.3.6.1.4.1.47477.10.21.31.3.42
		link31_2R2Power OBJECT-TYPE
			SYNTAX DisplayString
			MAX-ACCESS read-only
			STATUS current
			DESCRIPTION
				"get the power of 2R2 in link31."
			::= { link31OBP 42 }

--  1.3.6.1.4.1.47477.10.21.31.3.41
		-- 1.3.6.1.4.1.47477.10.21.31.3.43
		link31_2R3Power OBJECT-TYPE
			SYNTAX DisplayString
			MAX-ACCESS read-only
			STATUS current
			DESCRIPTION
				"get the power of 2R3 in link31."
			::= { link31OBP 43 }
			
--  1.3.6.1.4.1.47477.10.21.31.3.42
		-- 1.3.6.1.4.1.47477.10.21.31.3.44
		link31_2R4Power OBJECT-TYPE
			SYNTAX DisplayString
			MAX-ACCESS read-only
			STATUS current
			DESCRIPTION
				"get the power of 2R4 in link31."
			::= { link31OBP 44 }
			
--  1.3.6.1.4.1.47477.10.21.31.3.49
		-- 1.3.6.1.4.1.47477.10.21.31.3.49
		link31_1R1Wave OBJECT-TYPE
			SYNTAX INTEGER
				{
				w850nm(0),
				na(2)
				}
			MAX-ACCESS read-only
			STATUS current
			DESCRIPTION
				"get the wave length of 1R1 in link31."
			::= { link31OBP 49 }
		
--  1.3.6.1.4.1.47477.10.21.31.3.60
		-- 1.3.6.1.4.1.47477.10.21.31.3.60
		link31_1R2Wave OBJECT-TYPE
			SYNTAX INTEGER
				{
				w850nm(0),
				na(2)
				}
			MAX-ACCESS read-only
			STATUS current
			DESCRIPTION
				"get the wave length of 1R2 in link31."
			::= { link31OBP 60 }

--  1.3.6.1.4.1.47477.10.21.31.3.61
		-- 1.3.6.1.4.1.47477.10.21.31.3.61
		link31_1R3Wave OBJECT-TYPE
			SYNTAX INTEGER
				{
				w850nm(0),
				na(2)
				}
			MAX-ACCESS read-only
			STATUS current
			DESCRIPTION
				"get the wave length of 1R3 in link31."
			::= { link31OBP 61 }

		
--  1.3.6.1.4.1.47477.10.21.31.3.62
		-- 1.3.6.1.4.1.47477.10.21.31.3.62
		link31_1R4Wave OBJECT-TYPE
			SYNTAX INTEGER
				{
				w850nm(0),
				na(2)
				}
			MAX-ACCESS read-only
			STATUS current
			DESCRIPTION
				"get the wave length of 1R4 in link31."
			::= { link31OBP 62 }
	
--  1.3.6.1.4.1.47477.10.21.31.3.63
		-- 1.3.6.1.4.1.47477.10.21.31.3.63
		link31_2R1Wave OBJECT-TYPE
			SYNTAX INTEGER
				{
				w850nm(0),
				na(2)
				}
			MAX-ACCESS read-only
			STATUS current
			DESCRIPTION
				"get the wave length of 2R1 in link31."
			::= { link31OBP 63 }

		
--  1.3.6.1.4.1.47477.10.21.31.3.64
		-- 1.3.6.1.4.1.47477.10.21.31.3.64
		link31_2R2Wave OBJECT-TYPE
			SYNTAX INTEGER
				{
				w850nm(0),
				na(2)
				}
			MAX-ACCESS read-only
			STATUS current
			DESCRIPTION
				"get the wave length of 2R2 in link31."
			::= { link31OBP 64 }	
	
--  1.3.6.1.4.1.47477.10.21.31.3.65
		-- 1.3.6.1.4.1.47477.10.21.31.3.65
		link31_2R3Wave OBJECT-TYPE
			SYNTAX INTEGER
				{
				w850nm(0),
				na(2)
				}
			MAX-ACCESS read-only
			STATUS current
			DESCRIPTION
				"get the wave length of 2R3 in link31."
			::= { link31OBP 65 }

		
--  1.3.6.1.4.1.47477.10.21.31.3.66
		-- 1.3.6.1.4.1.47477.10.21.31.3.66
		link31_2R4Wave OBJECT-TYPE
			SYNTAX INTEGER
				{
				w850nm(0),
				na(2)
				}
			MAX-ACCESS read-only
			STATUS current
			DESCRIPTION
				"get the wave length of 2R4 in link31."
			::= { link31OBP 66 }	
			
--  1.3.6.1.4.1.47477.10.21.31.3.31
		-- 1.3.6.1.4.1.47477.10.21.31.3.31
		link31_1R1AlarmPower OBJECT-TYPE
			SYNTAX DisplayString
			MAX-ACCESS read-write
			STATUS current
			DESCRIPTION
				"get or set the power alarm threshold of 1R1 in link31."
			::= { link31OBP 31 }
			
--  1.3.6.1.4.1.47477.10.21.31.3.32
		-- 1.3.6.1.4.1.47477.10.21.31.3.32
		link31_1R2AlarmPower OBJECT-TYPE
			SYNTAX DisplayString
			MAX-ACCESS read-write
			STATUS current
			DESCRIPTION
				"get or set the power alarm threshold of 1R2 in link31."
			::= { link31OBP 32 }

--  1.3.6.1.4.1.47477.10.21.31.3.33
		-- 1.3.6.1.4.1.47477.10.21.31.3.33
		link31_1R3AlarmPower OBJECT-TYPE
			SYNTAX DisplayString
			MAX-ACCESS read-write
			STATUS current
			DESCRIPTION
				"get or set the power alarm threshold of 1R3 in link31."
			::= { link31OBP 33 }
			
--  1.3.6.1.4.1.47477.10.21.31.3.34
		-- 1.3.6.1.4.1.47477.10.21.31.3.34
		link31_1R4AlarmPower OBJECT-TYPE
			SYNTAX DisplayString
			MAX-ACCESS read-write
			STATUS current
			DESCRIPTION
				"get or set the power alarm threshold of 1R4 in link31."
			::= { link31OBP 34 }

--  1.3.6.1.4.1.47477.10.21.31.3.45
		-- 1.3.6.1.4.1.47477.10.21.31.3.45
		link31_2R1AlarmPower OBJECT-TYPE
			SYNTAX DisplayString
			MAX-ACCESS read-write
			STATUS current
			DESCRIPTION
				"get or set the power alarm threshold of 2R1 in link31."
			::= { link31OBP 45 }
			
--  1.3.6.1.4.1.47477.10.21.31.3.46
		-- 1.3.6.1.4.1.47477.10.21.31.3.46
		link31_2R2AlarmPower OBJECT-TYPE
			SYNTAX DisplayString
			MAX-ACCESS read-write
			STATUS current
			DESCRIPTION
				"get or set the power alarm threshold of 2R2 in link31."
			::= { link31OBP 46 }

--  1.3.6.1.4.1.47477.10.21.31.3.47
		-- 1.3.6.1.4.1.47477.10.21.31.3.47
		link31_2R3AlarmPower OBJECT-TYPE
			SYNTAX DisplayString
			MAX-ACCESS read-write
			STATUS current
			DESCRIPTION
				"get or set the power alarm threshold of 2R3 in link31."
			::= { link31OBP 47 }
			
--  1.3.6.1.4.1.47477.10.21.31.3.48
		-- 1.3.6.1.4.1.47477.10.21.31.3.48
		link31_2R4AlarmPower OBJECT-TYPE
			SYNTAX DisplayString
			MAX-ACCESS read-write
			STATUS current
			DESCRIPTION
				"get or set the power alarm threshold of 2R4 in link31."
			::= { link31OBP 48 }
			
--  1.3.6.1.4.1.47477.10.21.31.3.11
		-- 1.3.6.1.4.1.47477.10.21.31.3.11
		link31_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link31OBP 11 }
			
--  1.3.6.1.4.1.47477.10.21.31.3.67
		-- 1.3.6.1.4.1.47477.10.21.31.3.67
		link31_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link31OBP 67 }
			
--  1.3.6.1.4.1.47477.10.21.31.3.68
		-- 1.3.6.1.4.1.47477.10.21.31.3.68
		link31_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link31OBP 68 }
			
--  1.3.6.1.4.1.47477.10.21.31.3.12
		-- 1.3.6.1.4.1.47477.10.21.31.3.12
		link31_ReturnDelay OBJECT-TYPE
			--SYNTAX Integer32
			SYNTAX Integer32
			MAX-ACCESS read-write
			STATUS current
			DESCRIPTION
				"get or set how long link31 takes to return to automatic mode."
			::= { link31OBP 12 }
			
--  1.3.6.1.4.1.47477.10.21.31.3.13
		-- 1.3.6.1.4.1.47477.10.21.31.3.13
		link31_BackMode OBJECT-TYPE
			SYNTAX INTEGER
				{
				autoNoBack(0),
				autoBack(1)
				}
			MAX-ACCESS read-write
			STATUS current
			DESCRIPTION
				"get or set the back mode of link31."
			::= { link31OBP 13 }

		
--  1.3.6.1.4.1.47477.10.21.31.3.14
		-- 1.3.6.1.4.1.47477.10.21.31.3.14
		link31_BackDelay OBJECT-TYPE
			SYNTAX Integer32
			MAX-ACCESS read-write
			STATUS current
			DESCRIPTION
				"get or set the back delay."
			::= { link31OBP 14 }

--  1.3.6.1.4.1.47477.10.21.31.3.15
		-- 1.3.6.1.4.1.47477.10.21.31.3.15
		link31_ActiveHeartSwitch OBJECT-TYPE
			SYNTAX INTEGER
				{
				off(0),
				on(1)
				}
			MAX-ACCESS read-write
			STATUS current
			DESCRIPTION
				"get or set the switch status of active heartbeat."
			::= { link31OBP 15 }

		
--  1.3.6.1.4.1.47477.10.21.31.3.16
		-- 1.3.6.1.4.1.47477.10.21.31.3.16
		link31_ActiveSendInterval OBJECT-TYPE
			SYNTAX Integer32
			MAX-ACCESS read-write
			STATUS current
			DESCRIPTION
				"get or set the send interval of active heartbeat."
			::= { link31OBP 16 }		

--  1.3.6.1.4.1.47477.10.21.31.3.17
		-- 1.3.6.1.4.1.47477.10.21.31.3.17
		link31_ActiveTimeOut OBJECT-TYPE
			SYNTAX Integer32
			MAX-ACCESS read-write
			STATUS current
			DESCRIPTION
				"get or set how long the active heartbeat send timeout."
			::= { link31OBP 17 }

--  1.3.6.1.4.1.47477.10.21.31.3.18
		-- 1.3.6.1.4.1.47477.10.21.31.3.18
		link31_ActiveLossBypass OBJECT-TYPE
			SYNTAX Integer32
			MAX-ACCESS read-write
			STATUS current
			DESCRIPTION
				"get or set the bypass for active heartbeat packet loss."
			::= { link31OBP 18 }

--  1.3.6.1.4.1.47477.10.21.31.3.19
		-- 1.3.6.1.4.1.47477.10.21.31.3.19
		link31_PingIpAddress OBJECT-TYPE
			SYNTAX IpAddress
			MAX-ACCESS read-write
			STATUS current
			DESCRIPTION
				"get or set the ping ip address of link31."
			::= { link31OBP 19 }

--  1.3.6.1.4.1.47477.10.21.31.3.20
		-- 1.3.6.1.4.1.47477.10.21.31.3.20
		link31_PassiveHeartSwitch OBJECT-TYPE
			SYNTAX INTEGER
				{
				off(0),
				on(1)
				}
			MAX-ACCESS read-write
			STATUS current
			DESCRIPTION
				"get or set the switch status of passive heartbeat."
			::= { link31OBP 20 }
	

--  1.3.6.1.4.1.47477.10.21.31.3.21
		-- 1.3.6.1.4.1.47477.10.21.31.3.21
		link31_PassiveTimeOut OBJECT-TYPE
			SYNTAX Integer32
			MAX-ACCESS read-write
			STATUS current
			DESCRIPTION
				"get or set how long the passive heartbeat send timeout."
			::= { link31OBP 21 }

--  1.3.6.1.4.1.47477.10.21.31.3.22
		-- 1.3.6.1.4.1.47477.10.21.31.3.22
		link31_PassiveLossBypass OBJECT-TYPE
			SYNTAX Integer32
			MAX-ACCESS read-write
			STATUS current
			DESCRIPTION
				"get or set the bypass for passive heartbeat packet loss."
			::= { link31OBP 22 }

--  1.3.6.1.4.1.47477.10.21.31.3.23
		-- 1.3.6.1.4.1.47477.10.21.31.3.23
		link31_SwitchProtect OBJECT-TYPE
			SYNTAX INTEGER
				{
				off(0),
				on(1)
				}
			MAX-ACCESS read-write
			STATUS current
			DESCRIPTION
				"get or set the switch protection status of link31."
			::= { link31OBP 23 }
			
--  1.3.6.1.4.1.47477.10.21.31.3.24
		-- 1.3.6.1.4.1.47477.10.21.31.3.24
		link31_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link31OBP 24 }		

--  1.3.6.1.4.1.47477.10.21.31.3.25
		-- 1.3.6.1.4.1.47477.10.21.31.3.25
		link31_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link31OBP 25 }	

--  1.3.6.1.4.1.47477.10.21.31.3.26
		-- 1.3.6.1.4.1.47477.10.21.31.3.26
		link31_PowerAlarmStatus OBJECT-TYPE
			SYNTAX INTEGER
				{
				off(0),
				alarm(1),
				normal(2),
				na(3)
				}
			MAX-ACCESS read-only
			STATUS current
			DESCRIPTION
				"get whether a power alarm is generated."
			::= { link31OBP 26 }	


-- 1.3.6.1.4.1.47477.10.21.31.3.50.1
	link31_WorkModeChange 	OBJECT-TYPE    
    SYNTAX INTEGER	{
				manualMode(0),
				autoMode(1)
		}
	MAX-ACCESS read-only
	STATUS current
    DESCRIPTION
        "The Link mode Changed."
    ::= {link31OBPTrap 1}

-- 1.3.6.1.4.1.47477.10.21.31.3.50.2
	link31_StateChange 	OBJECT-TYPE    
    SYNTAX INTEGER	{
				bypass(0),
				primary(1)
		}
	MAX-ACCESS read-only
	STATUS current
    DESCRIPTION
        "The Link State(Channel) Changed."
    ::= {link31OBPTrap 2}

-- 1.3.6.1.4.1.47477.10.21.31.3.50.3
	link31_R1WaveSet 	OBJECT-TYPE    
    SYNTAX INTEGER	{
				w1310nm(0),
				w1550nm(1)
		}
	MAX-ACCESS read-only
	STATUS current
    DESCRIPTION
        "Set The link31 R1 Wave."
    ::= {link31OBPTrap 3}

-- 1.3.6.1.4.1.47477.10.21.31.3.50.4
	link31_R2WaveSet 	OBJECT-TYPE    
    SYNTAX INTEGER	{
				w1310nm(0),
				w1550nm(1)
		}
	MAX-ACCESS read-only
	STATUS current
    DESCRIPTION
        "Set The link31 R2 Wave."
    ::= {link31OBPTrap 4}			

-- 1.3.6.1.4.1.47477.10.21.31.3.50.5
	link31_R3WaveSet 	OBJECT-TYPE    
    SYNTAX INTEGER	{
				w1310nm(0),
				w1550nm(1)
		}
	MAX-ACCESS read-only
	STATUS current
    DESCRIPTION
        "Set The link31 R3 Wave."
    ::= {link31OBPTrap 5}

-- 1.3.6.1.4.1.47477.10.21.31.3.50.6
	link31_R4WaveSet 	OBJECT-TYPE    
    SYNTAX INTEGER	{
				w1310nm(0),
				w1550nm(1)
		}
	MAX-ACCESS read-only
	STATUS current
    DESCRIPTION
        "Set The link31 R4 Wave."
    ::= {link31OBPTrap 6}	
	
-- 1.3.6.1.4.1.47477.10.21.31.3.50.7
	link31_R1AlarmSet 	OBJECT-TYPE    
    SYNTAX DisplayString
	MAX-ACCESS read-only
	STATUS current
    DESCRIPTION
        "Set The link31 R1 Alarm Threshold."
    ::= {link31OBPTrap 7}

-- 1.3.6.1.4.1.47477.10.21.31.3.50.8
	link31_R2AlarmSet 	OBJECT-TYPE    
    SYNTAX DisplayString
	MAX-ACCESS read-only
	STATUS current
    DESCRIPTION
        "Set The link31 R2 Alarm Threshold."
    ::= {link31OBPTrap 8}
	
-- 1.3.6.1.4.1.47477.10.21.31.3.50.9
	link31_R3AlarmSet 	OBJECT-TYPE    
    SYNTAX DisplayString
	MAX-ACCESS read-only
	STATUS current
    DESCRIPTION
        "Set The link31 R3 Alarm Threshold."
    ::= {link31OBPTrap 9}

-- 1.3.6.1.4.1.47477.10.21.31.3.50.10
	link31_R4AlarmSet 	OBJECT-TYPE    
    SYNTAX DisplayString
	MAX-ACCESS read-only
	STATUS current
    DESCRIPTION
        "Set The link31 R4 Alarm Threshold."
    ::= {link31OBPTrap 10}	
	
	
-- 1.3.6.1.4.1.47477.10.21.31.3.50.11
	link31_1R1AlarmSet 	OBJECT-TYPE    
    SYNTAX DisplayString
	MAX-ACCESS read-only
	STATUS current
    DESCRIPTION
        "Set The link31 1R1 Alarm Threshold."
    ::= {link31OBPTrap 11}

-- 1.3.6.1.4.1.47477.10.21.31.3.50.12
	link31_2R1AlarmSet 	OBJECT-TYPE    
    SYNTAX DisplayString
	MAX-ACCESS read-only
	STATUS current
    DESCRIPTION
        "Set The link31 2R1 Alarm Threshold."
    ::= {link31OBPTrap 12}
	
-- 1.3.6.1.4.1.47477.10.21.31.3.50.13
	link31_1R2AlarmSet 	OBJECT-TYPE    
    SYNTAX DisplayString
	MAX-ACCESS read-only
	STATUS current
    DESCRIPTION
        "Set The link31 1R2 Alarm Threshold."
    ::= {link31OBPTrap 13}

-- 1.3.6.1.4.1.47477.10.21.31.3.50.14
	link31_2R2AlarmSet 	OBJECT-TYPE    
    SYNTAX DisplayString
	MAX-ACCESS read-only
	STATUS current
    DESCRIPTION
        "Set The link31 2R2 Alarm Threshold."
    ::= {link31OBPTrap 14}
	
-- 1.3.6.1.4.1.47477.10.21.31.3.50.15
	link31_1R3AlarmSet 	OBJECT-TYPE    
    SYNTAX DisplayString
	MAX-ACCESS read-only
	STATUS current
    DESCRIPTION
        "Set The link31 1R3 Alarm Threshold."
    ::= {link31OBPTrap 15}

-- 1.3.6.1.4.1.47477.10.21.31.3.50.16
	link31_2R3AlarmSet 	OBJECT-TYPE    
    SYNTAX DisplayString
	MAX-ACCESS read-only
	STATUS current
    DESCRIPTION
        "Set The link31 2R3 Alarm Threshold."
    ::= {link31OBPTrap 16}
	
-- 1.3.6.1.4.1.47477.10.21.31.3.50.17
	link31_1R4AlarmSet 	OBJECT-TYPE    
    SYNTAX DisplayString
	MAX-ACCESS read-only
	STATUS current
    DESCRIPTION
        "Set The link31 1R4 Alarm Threshold."
    ::= {link31OBPTrap 17}

-- 1.3.6.1.4.1.47477.10.21.31.3.50.18
	link31_2R4AlarmSet 	OBJECT-TYPE    
    SYNTAX DisplayString
	MAX-ACCESS read-only
	STATUS current
    DESCRIPTION
        "Set The link31 2R4 Alarm Threshold."
    ::= {link31OBPTrap 18}
	
-- 1.3.6.1.4.1.47477.10.21.31.3.50.19
	link31_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link31 PowerAlarmBypass2 Changed."
    ::= {link31OBPTrap 19}
	
-- 1.3.6.1.4.1.47477.10.21.31.3.50.20
	link31_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link31 PowerAlarmBypass4 Changed."
    ::= {link31OBPTrap 20}	
	
-- 1.3.6.1.4.1.47477.10.21.31.3.50.21
	link31_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link31 PowerAlarmBypass8 Changed."
    ::= {link31OBPTrap 21}
	
-- 1.3.6.1.4.1.47477.10.21.31.3.50.22
	link31_powerAlarmR1 	OBJECT-TYPE    
    SYNTAX DisplayString
	MAX-ACCESS read-only
	STATUS current
    DESCRIPTION
        "Set The link31 R1 Power Status Alarm."
    ::= {link31OBPTrap 22}
	
-- 1.3.6.1.4.1.47477.10.21.31.3.50.23
	link31_powerAlarmR2 	OBJECT-TYPE    
    SYNTAX DisplayString
	MAX-ACCESS read-only
	STATUS current
    DESCRIPTION
        "Set The link31 R2 Power Status Alarm."
    ::= {link31OBPTrap 23}
	
-- 1.3.6.1.4.1.47477.10.21.31.3.50.24
	link31_powerAlarmR3 	OBJECT-TYPE    
    SYNTAX DisplayString
	MAX-ACCESS read-only
	STATUS current
    DESCRIPTION
        "Set The link31 R3 Power Status Alarm."
    ::= {link31OBPTrap 24}
	
-- 1.3.6.1.4.1.47477.10.21.31.3.50.25
	link31_powerAlarmR4 	OBJECT-TYPE    
    SYNTAX DisplayString
	MAX-ACCESS read-only
	STATUS current
    DESCRIPTION
        "Set The link31 R4 Power Status Alarm."
    ::= {link31OBPTrap 25}
	
	
-- 1.3.6.1.4.1.47477.10.21.31.3.50.26
	link31_powerAlarm1R1 	OBJECT-TYPE    
    SYNTAX DisplayString
	MAX-ACCESS read-only
	STATUS current
    DESCRIPTION
        "Set The link31 1R1 Power Status Alarm."
    ::= {link31OBPTrap 26}
	
-- 1.3.6.1.4.1.47477.10.21.31.3.50.27
	link31_powerAlarm2R1 	OBJECT-TYPE    
    SYNTAX DisplayString
	MAX-ACCESS read-only
	STATUS current
    DESCRIPTION
        "Set The link31 2R1 Power Status Alarm."
    ::= {link31OBPTrap 27}
	
-- 1.3.6.1.4.1.47477.10.21.31.3.50.28
	link31_powerAlarm1R2 	OBJECT-TYPE    
    SYNTAX DisplayString
	MAX-ACCESS read-only
	STATUS current
    DESCRIPTION
        "Set The link31 1R2 Power Status Alarm."
    ::= {link31OBPTrap 28}
	
-- 1.3.6.1.4.1.47477.10.21.31.3.50.29
	link31_powerAlarm2R2 	OBJECT-TYPE    
    SYNTAX DisplayString
	MAX-ACCESS read-only
	STATUS current
    DESCRIPTION
        "Set The link31 2R2 Power Status Alarm."
    ::= {link31OBPTrap 29}
	
-- 1.3.6.1.4.1.47477.10.21.31.3.50.30
	link31_powerAlarm1R3 	OBJECT-TYPE    
    SYNTAX DisplayString
	MAX-ACCESS read-only
	STATUS current
    DESCRIPTION
        "Set The link31 1R3 Power Status Alarm."
    ::= {link31OBPTrap 30}
	
-- 1.3.6.1.4.1.47477.10.21.31.3.50.31
	link31_powerAlarm2R3 	OBJECT-TYPE    
    SYNTAX DisplayString
	MAX-ACCESS read-only
	STATUS current
    DESCRIPTION
        "Set The link31 2R1 Power Status Alarm."
    ::= {link31OBPTrap 31}
	
-- 1.3.6.1.4.1.47477.10.21.31.3.50.32
	link31_powerAlarm1R4 	OBJECT-TYPE    
    SYNTAX DisplayString
	MAX-ACCESS read-only
	STATUS current
    DESCRIPTION
        "Set The link31 1R4 Power Status Alarm."
    ::= {link31OBPTrap 32}
	
-- 1.3.6.1.4.1.47477.10.21.31.3.50.33
	link31_powerAlarm2R4 	OBJECT-TYPE    
    SYNTAX DisplayString
	MAX-ACCESS read-only
	STATUS current
    DESCRIPTION
        "Set The link31 2R4 Power Status Alarm."
    ::= {link31OBPTrap 33}
	
--  1.3.6.1.4.1.47477.10.21.32.3.1
		-- 1.3.6.1.4.1.47477.10.21.32.3.1
		link32_State OBJECT-TYPE
			SYNTAX INTEGER
				{
				off(0),
				on(1)
				}
			MAX-ACCESS read-only
			STATUS current
			DESCRIPTION
				"get the information about whether link32 is working."
			::= { link32OBP 1 }

		
--  1.3.6.1.4.1.47477.10.21.32.3.2
		-- 1.3.6.1.4.1.47477.10.21.32.3.2
		link32_DeviceType OBJECT-TYPE
			SYNTAX DisplayString
			MAX-ACCESS read-only
			STATUS current
			DESCRIPTION
				"get the type of card in link32."
			::= { link32OBP 2 }

			
--  1.3.6.1.4.1.47477.10.21.32.3.3
		-- 1.3.6.1.4.1.47477.10.21.32.3.3
		link32_WorkMode OBJECT-TYPE
			SYNTAX INTEGER
				{
				manualMode(0),
				autoMode(1)
				}
			MAX-ACCESS read-write
			STATUS current
			DESCRIPTION
				"get or set link32's work mode."
			::= { link32OBP 3 }

		
--  1.3.6.1.4.1.47477.10.21.32.3.4
		-- 1.3.6.1.4.1.47477.10.21.32.3.4
		link32_Channel OBJECT-TYPE
			SYNTAX INTEGER
				{
				bypass(0),
				primary(1)
				}
			MAX-ACCESS read-write
			STATUS current
			DESCRIPTION
				"get or set the channel in which link32 works."
			::= { link32OBP 4 }


--  1.3.6.1.4.1.47477.10.21.32.3.5
		-- 1.3.6.1.4.1.47477.10.21.32.3.5
		link32_R1Power OBJECT-TYPE
			SYNTAX DisplayString
			MAX-ACCESS read-only
			STATUS current
			DESCRIPTION
				"get the power of R1 in link32."
			::= { link32OBP 5 }

		
--  1.3.6.1.4.1.47477.10.21.32.3.6
		-- 1.3.6.1.4.1.47477.10.21.32.3.6
		link32_R2Power OBJECT-TYPE
			SYNTAX DisplayString
			MAX-ACCESS read-only
			STATUS current
			DESCRIPTION
				"get the power of R2 in link32."
			::= { link32OBP 6 }
			
--  1.3.6.1.4.1.47477.10.21.32.3.35
		-- 1.3.6.1.4.1.47477.10.21.32.3.35
		link32_R3Power OBJECT-TYPE
			SYNTAX DisplayString
			MAX-ACCESS read-only
			STATUS current
			DESCRIPTION
				"get the power of R3 in link32."
			::= { link32OBP 35 }
			
--  1.3.6.1.4.1.47477.10.21.32.3.36
		-- 1.3.6.1.4.1.47477.10.21.32.3.36
		link32_R4Power OBJECT-TYPE
			SYNTAX DisplayString
			MAX-ACCESS read-only
			STATUS current
			DESCRIPTION
				"get the power of R4 in link32."
			::= { link32OBP 36 }		
		
--  1.3.6.1.4.1.47477.10.21.32.3.7
		-- 1.3.6.1.4.1.47477.10.21.32.3.7
		link32_R1Wave OBJECT-TYPE
			SYNTAX INTEGER
				{
				w1310nm(0),
				w1550nm(1),
				na(2)
				}
			MAX-ACCESS read-write
			STATUS current
			DESCRIPTION
				"get or set the wave length of R1 in link32."
			::= { link32OBP 7 }

		
--  1.3.6.1.4.1.47477.10.21.32.3.8
		-- 1.3.6.1.4.1.47477.10.21.32.3.8
		link32_R2Wave OBJECT-TYPE
			SYNTAX INTEGER
				{
				w1310nm(0),
				w1550nm(1),
				na(2)
				}
			MAX-ACCESS read-write
			STATUS current
			DESCRIPTION
				"get or set the wave length of R2 in link32."
			::= { link32OBP 8 }


--  1.3.6.1.4.1.47477.10.21.32.3.27
		-- 1.3.6.1.4.1.47477.10.21.32.3.27
		link32_R3Wave OBJECT-TYPE
			SYNTAX INTEGER
				{
				w1310nm(0),
				w1550nm(1),
				na(2)
				}
			MAX-ACCESS read-write
			STATUS current
			DESCRIPTION
				"get or set the wave length of R3 in link32."
			::= { link32OBP 27 }

		
--  1.3.6.1.4.1.47477.10.21.32.3.28
		-- 1.3.6.1.4.1.47477.10.21.32.3.28
		link32_R4Wave OBJECT-TYPE
			SYNTAX INTEGER
				{
				w1310nm(0),
				w1550nm(1),
				na(2)
				}
			MAX-ACCESS read-write
			STATUS current
			DESCRIPTION
				"get or set the wave length of R4 in link32."
			::= { link32OBP 28 }
			
--  1.3.6.1.4.1.47477.10.21.32.3.9
		-- 1.3.6.1.4.1.47477.10.21.32.3.9
		link32_R1AlarmPower OBJECT-TYPE
			SYNTAX DisplayString
			MAX-ACCESS read-write
			STATUS current
			DESCRIPTION
				"get or set the power alarm threshold of R1 in link32."
			::= { link32OBP 9 }

		
--  1.3.6.1.4.1.47477.10.21.32.3.10
		-- 1.3.6.1.4.1.47477.10.21.32.3.10
		link32_R2AlarmPower OBJECT-TYPE
			SYNTAX DisplayString
			MAX-ACCESS read-write
			STATUS current
			DESCRIPTION
				"get or set the power alarm threshold of R2 in link32."
			::= { link32OBP 10 }


--  1.3.6.1.4.1.47477.10.21.32.3.29
		-- 1.3.6.1.4.1.47477.10.21.32.3.29
		link32_R3AlarmPower OBJECT-TYPE
			SYNTAX DisplayString
			MAX-ACCESS read-write
			STATUS current
			DESCRIPTION
				"get or set the power alarm threshold of R3 in link32."
			::= { link32OBP 29 }

		
--  1.3.6.1.4.1.47477.10.21.32.3.30
		-- 1.3.6.1.4.1.47477.10.21.32.3.30
		link32_R4AlarmPower OBJECT-TYPE
			SYNTAX DisplayString
			MAX-ACCESS read-write
			STATUS current
			DESCRIPTION
				"get or set the power alarm threshold of R4 in link32."
			::= { link32OBP 30 }

-- OBP4
--  1.3.6.1.4.1.47477.10.21.32.3.37
		-- 1.3.6.1.4.1.47477.10.21.32.3.37
		link32_1R1Power OBJECT-TYPE
			SYNTAX DisplayString
			MAX-ACCESS read-only
			STATUS current
			DESCRIPTION
				"get the power of 1R1 in link32."
			::= { link32OBP 37 }
			
--  1.3.6.1.4.1.47477.10.21.32.3.38
		-- 1.3.6.1.4.1.47477.10.21.32.3.38
		link32_1R2Power OBJECT-TYPE
			SYNTAX DisplayString
			MAX-ACCESS read-only
			STATUS current
			DESCRIPTION
				"get the power of 1R2 in link32."
			::= { link32OBP 38 }

--  1.3.6.1.4.1.47477.10.21.32.3.39
		-- 1.3.6.1.4.1.47477.10.21.32.3.39
		link32_1R3Power OBJECT-TYPE
			SYNTAX DisplayString
			MAX-ACCESS read-only
			STATUS current
			DESCRIPTION
				"get the power of 1R3 in link32."
			::= { link32OBP 39 }
			
--  1.3.6.1.4.1.47477.10.21.32.3.40
		-- 1.3.6.1.4.1.47477.10.21.32.3.40
		link32_1R4Power OBJECT-TYPE
			SYNTAX DisplayString
			MAX-ACCESS read-only
			STATUS current
			DESCRIPTION
				"get the power of 1R4 in link32."
			::= { link32OBP 40 }

--  1.3.6.1.4.1.47477.10.21.32.3.41
		-- 1.3.6.1.4.1.47477.10.21.32.3.41
		link32_2R1Power OBJECT-TYPE
			SYNTAX DisplayString
			MAX-ACCESS read-only
			STATUS current
			DESCRIPTION
				"get the power of 2R1 in link32."
			::= { link32OBP 41 }
			
--  1.3.6.1.4.1.47477.10.21.32.3.42
		-- 1.3.6.1.4.1.47477.10.21.32.3.42
		link32_2R2Power OBJECT-TYPE
			SYNTAX DisplayString
			MAX-ACCESS read-only
			STATUS current
			DESCRIPTION
				"get the power of 2R2 in link32."
			::= { link32OBP 42 }

--  1.3.6.1.4.1.47477.10.21.32.3.41
		-- 1.3.6.1.4.1.47477.10.21.32.3.43
		link32_2R3Power OBJECT-TYPE
			SYNTAX DisplayString
			MAX-ACCESS read-only
			STATUS current
			DESCRIPTION
				"get the power of 2R3 in link32."
			::= { link32OBP 43 }
			
--  1.3.6.1.4.1.47477.10.21.32.3.42
		-- 1.3.6.1.4.1.47477.10.21.32.3.44
		link32_2R4Power OBJECT-TYPE
			SYNTAX DisplayString
			MAX-ACCESS read-only
			STATUS current
			DESCRIPTION
				"get the power of 2R4 in link32."
			::= { link32OBP 44 }
			
--  1.3.6.1.4.1.47477.10.21.32.3.49
		-- 1.3.6.1.4.1.47477.10.21.32.3.49
		link32_1R1Wave OBJECT-TYPE
			SYNTAX INTEGER
				{
				w850nm(0),
				na(2)
				}
			MAX-ACCESS read-only
			STATUS current
			DESCRIPTION
				"get the wave length of 1R1 in link32."
			::= { link32OBP 49 }
		
--  1.3.6.1.4.1.47477.10.21.32.3.60
		-- 1.3.6.1.4.1.47477.10.21.32.3.60
		link32_1R2Wave OBJECT-TYPE
			SYNTAX INTEGER
				{
				w850nm(0),
				na(2)
				}
			MAX-ACCESS read-only
			STATUS current
			DESCRIPTION
				"get the wave length of 1R2 in link32."
			::= { link32OBP 60 }

--  1.3.6.1.4.1.47477.10.21.32.3.61
		-- 1.3.6.1.4.1.47477.10.21.32.3.61
		link32_1R3Wave OBJECT-TYPE
			SYNTAX INTEGER
				{
				w850nm(0),
				na(2)
				}
			MAX-ACCESS read-only
			STATUS current
			DESCRIPTION
				"get the wave length of 1R3 in link32."
			::= { link32OBP 61 }

		
--  1.3.6.1.4.1.47477.10.21.32.3.62
		-- 1.3.6.1.4.1.47477.10.21.32.3.62
		link32_1R4Wave OBJECT-TYPE
			SYNTAX INTEGER
				{
				w850nm(0),
				na(2)
				}
			MAX-ACCESS read-only
			STATUS current
			DESCRIPTION
				"get the wave length of 1R4 in link32."
			::= { link32OBP 62 }
	
--  1.3.6.1.4.1.47477.10.21.32.3.63
		-- 1.3.6.1.4.1.47477.10.21.32.3.63
		link32_2R1Wave OBJECT-TYPE
			SYNTAX INTEGER
				{
				w850nm(0),
				na(2)
				}
			MAX-ACCESS read-only
			STATUS current
			DESCRIPTION
				"get the wave length of 2R1 in link32."
			::= { link32OBP 63 }

		
--  1.3.6.1.4.1.47477.10.21.32.3.64
		-- 1.3.6.1.4.1.47477.10.21.32.3.64
		link32_2R2Wave OBJECT-TYPE
			SYNTAX INTEGER
				{
				w850nm(0),
				na(2)
				}
			MAX-ACCESS read-only
			STATUS current
			DESCRIPTION
				"get the wave length of 2R2 in link32."
			::= { link32OBP 64 }	
	
--  1.3.6.1.4.1.47477.10.21.32.3.65
		-- 1.3.6.1.4.1.47477.10.21.32.3.65
		link32_2R3Wave OBJECT-TYPE
			SYNTAX INTEGER
				{
				w850nm(0),
				na(2)
				}
			MAX-ACCESS read-only
			STATUS current
			DESCRIPTION
				"get the wave length of 2R3 in link32."
			::= { link32OBP 65 }

		
--  1.3.6.1.4.1.47477.10.21.32.3.66
		-- 1.3.6.1.4.1.47477.10.21.32.3.66
		link32_2R4Wave OBJECT-TYPE
			SYNTAX INTEGER
				{
				w850nm(0),
				na(2)
				}
			MAX-ACCESS read-only
			STATUS current
			DESCRIPTION
				"get the wave length of 2R4 in link32."
			::= { link32OBP 66 }	
			
--  1.3.6.1.4.1.47477.10.21.32.3.31
		-- 1.3.6.1.4.1.47477.10.21.32.3.31
		link32_1R1AlarmPower OBJECT-TYPE
			SYNTAX DisplayString
			MAX-ACCESS read-write
			STATUS current
			DESCRIPTION
				"get or set the power alarm threshold of 1R1 in link32."
			::= { link32OBP 31 }
			
--  1.3.6.1.4.1.47477.10.21.32.3.32
		-- 1.3.6.1.4.1.47477.10.21.32.3.32
		link32_1R2AlarmPower OBJECT-TYPE
			SYNTAX DisplayString
			MAX-ACCESS read-write
			STATUS current
			DESCRIPTION
				"get or set the power alarm threshold of 1R2 in link32."
			::= { link32OBP 32 }

--  1.3.6.1.4.1.47477.10.21.32.3.33
		-- 1.3.6.1.4.1.47477.10.21.32.3.33
		link32_1R3AlarmPower OBJECT-TYPE
			SYNTAX DisplayString
			MAX-ACCESS read-write
			STATUS current
			DESCRIPTION
				"get or set the power alarm threshold of 1R3 in link32."
			::= { link32OBP 33 }
			
--  1.3.6.1.4.1.47477.10.21.32.3.34
		-- 1.3.6.1.4.1.47477.10.21.32.3.34
		link32_1R4AlarmPower OBJECT-TYPE
			SYNTAX DisplayString
			MAX-ACCESS read-write
			STATUS current
			DESCRIPTION
				"get or set the power alarm threshold of 1R4 in link32."
			::= { link32OBP 34 }

--  1.3.6.1.4.1.47477.10.21.32.3.45
		-- 1.3.6.1.4.1.47477.10.21.32.3.45
		link32_2R1AlarmPower OBJECT-TYPE
			SYNTAX DisplayString
			MAX-ACCESS read-write
			STATUS current
			DESCRIPTION
				"get or set the power alarm threshold of 2R1 in link32."
			::= { link32OBP 45 }
			
--  1.3.6.1.4.1.47477.10.21.32.3.46
		-- 1.3.6.1.4.1.47477.10.21.32.3.46
		link32_2R2AlarmPower OBJECT-TYPE
			SYNTAX DisplayString
			MAX-ACCESS read-write
			STATUS current
			DESCRIPTION
				"get or set the power alarm threshold of 2R2 in link32."
			::= { link32OBP 46 }

--  1.3.6.1.4.1.47477.10.21.32.3.47
		-- 1.3.6.1.4.1.47477.10.21.32.3.47
		link32_2R3AlarmPower OBJECT-TYPE
			SYNTAX DisplayString
			MAX-ACCESS read-write
			STATUS current
			DESCRIPTION
				"get or set the power alarm threshold of 2R3 in link32."
			::= { link32OBP 47 }
			
--  1.3.6.1.4.1.47477.10.21.32.3.48
		-- 1.3.6.1.4.1.47477.10.21.32.3.48
		link32_2R4AlarmPower OBJECT-TYPE
			SYNTAX DisplayString
			MAX-ACCESS read-write
			STATUS current
			DESCRIPTION
				"get or set the power alarm threshold of 2R4 in link32."
			::= { link32OBP 48 }
			
--  1.3.6.1.4.1.47477.10.21.32.3.11
		-- 1.3.6.1.4.1.47477.10.21.32.3.11
		link32_PowerAlarmBypass2 OBJECT-TYPE
			SYNTAX INTEGER
				{
				off(0),
				powerAlarmR1(1),
				powerAlarmR2(2),
				anyAlarmR1-R2(3),
				allAlarmR1-R2(4),
				na(5)
				}
			MAX-ACCESS read-write
			STATUS current
			DESCRIPTION
				"get or set alarm mode."
			::= { link32OBP 11 }
			
--  1.3.6.1.4.1.47477.10.21.32.3.67
		-- 1.3.6.1.4.1.47477.10.21.32.3.67
		link32_PowerAlarmBypass4 OBJECT-TYPE
			SYNTAX INTEGER
				{
				off(0),
				powerAlarmR1(1),
				powerAlarmR2(2),
				powerAlarmR3(3),
				powerAlarmR4(4),
				anyAlarmR1-R4(5),
				allAlarmR1-R4(6),
				na(7)
				}
			MAX-ACCESS read-write
			STATUS current
			DESCRIPTION
				"get or set alarm mode."
			::= { link32OBP 67 }
			
--  1.3.6.1.4.1.47477.10.21.32.3.68
		-- 1.3.6.1.4.1.47477.10.21.32.3.68
		link32_PowerAlarmBypass8 OBJECT-TYPE
			SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10),
				na(11)
				}
			MAX-ACCESS read-write
			STATUS current
			DESCRIPTION
				"get or set alarm mode."
			::= { link32OBP 68 }
			
--  1.3.6.1.4.1.47477.10.21.32.3.12
		-- 1.3.6.1.4.1.47477.10.21.32.3.12
		link32_ReturnDelay OBJECT-TYPE
			--SYNTAX Integer32
			SYNTAX Integer32
			MAX-ACCESS read-write
			STATUS current
			DESCRIPTION
				"get or set how long link32 takes to return to automatic mode."
			::= { link32OBP 12 }
			
--  1.3.6.1.4.1.47477.10.21.32.3.13
		-- 1.3.6.1.4.1.47477.10.21.32.3.13
		link32_BackMode OBJECT-TYPE
			SYNTAX INTEGER
				{
				autoNoBack(0),
				autoBack(1)
				}
			MAX-ACCESS read-write
			STATUS current
			DESCRIPTION
				"get or set the back mode of link32."
			::= { link32OBP 13 }

		
--  1.3.6.1.4.1.47477.10.21.32.3.14
		-- 1.3.6.1.4.1.47477.10.21.32.3.14
		link32_BackDelay OBJECT-TYPE
			SYNTAX Integer32
			MAX-ACCESS read-write
			STATUS current
			DESCRIPTION
				"get or set the back delay."
			::= { link32OBP 14 }

--  1.3.6.1.4.1.47477.10.21.32.3.15
		-- 1.3.6.1.4.1.47477.10.21.32.3.15
		link32_ActiveHeartSwitch OBJECT-TYPE
			SYNTAX INTEGER
				{
				off(0),
				on(1)
				}
			MAX-ACCESS read-write
			STATUS current
			DESCRIPTION
				"get or set the switch status of active heartbeat."
			::= { link32OBP 15 }

		
--  1.3.6.1.4.1.47477.10.21.32.3.16
		-- 1.3.6.1.4.1.47477.10.21.32.3.16
		link32_ActiveSendInterval OBJECT-TYPE
			SYNTAX Integer32
			MAX-ACCESS read-write
			STATUS current
			DESCRIPTION
				"get or set the send interval of active heartbeat."
			::= { link32OBP 16 }		

--  1.3.6.1.4.1.47477.10.21.32.3.17
		-- 1.3.6.1.4.1.47477.10.21.32.3.17
		link32_ActiveTimeOut OBJECT-TYPE
			SYNTAX Integer32
			MAX-ACCESS read-write
			STATUS current
			DESCRIPTION
				"get or set how long the active heartbeat send timeout."
			::= { link32OBP 17 }

--  1.3.6.1.4.1.47477.10.21.32.3.18
		-- 1.3.6.1.4.1.47477.10.21.32.3.18
		link32_ActiveLossBypass OBJECT-TYPE
			SYNTAX Integer32
			MAX-ACCESS read-write
			STATUS current
			DESCRIPTION
				"get or set the bypass for active heartbeat packet loss."
			::= { link32OBP 18 }

--  1.3.6.1.4.1.47477.10.21.32.3.19
		-- 1.3.6.1.4.1.47477.10.21.32.3.19
		link32_PingIpAddress OBJECT-TYPE
			SYNTAX IpAddress
			MAX-ACCESS read-write
			STATUS current
			DESCRIPTION
				"get or set the ping ip address of link32."
			::= { link32OBP 19 }

--  1.3.6.1.4.1.47477.10.21.32.3.20
		-- 1.3.6.1.4.1.47477.10.21.32.3.20
		link32_PassiveHeartSwitch OBJECT-TYPE
			SYNTAX INTEGER
				{
				off(0),
				on(1)
				}
			MAX-ACCESS read-write
			STATUS current
			DESCRIPTION
				"get or set the switch status of passive heartbeat."
			::= { link32OBP 20 }
	

--  1.3.6.1.4.1.47477.10.21.32.3.21
		-- 1.3.6.1.4.1.47477.10.21.32.3.21
		link32_PassiveTimeOut OBJECT-TYPE
			SYNTAX Integer32
			MAX-ACCESS read-write
			STATUS current
			DESCRIPTION
				"get or set how long the passive heartbeat send timeout."
			::= { link32OBP 21 }

--  1.3.6.1.4.1.47477.10.21.32.3.22
		-- 1.3.6.1.4.1.47477.10.21.32.3.22
		link32_PassiveLossBypass OBJECT-TYPE
			SYNTAX Integer32
			MAX-ACCESS read-write
			STATUS current
			DESCRIPTION
				"get or set the bypass for passive heartbeat packet loss."
			::= { link32OBP 22 }

--  1.3.6.1.4.1.47477.10.21.32.3.23
		-- 1.3.6.1.4.1.47477.10.21.32.3.23
		link32_SwitchProtect OBJECT-TYPE
			SYNTAX INTEGER
				{
				off(0),
				on(1)
				}
			MAX-ACCESS read-write
			STATUS current
			DESCRIPTION
				"get or set the switch protection status of link32."
			::= { link32OBP 23 }
			
--  1.3.6.1.4.1.47477.10.21.32.3.24
		-- 1.3.6.1.4.1.47477.10.21.32.3.24
		link32_ActiveHeartStatus OBJECT-TYPE
			SYNTAX INTEGER
				{
				alarm(0),
				normal(1),
				off(2),
				na(3)
				}
			MAX-ACCESS read-only
			STATUS current
			DESCRIPTION
				"get the active heartbeat status,such as whether work in alarm mode."
			::= { link32OBP 24 }		

--  1.3.6.1.4.1.47477.10.21.32.3.25
		-- 1.3.6.1.4.1.47477.10.21.32.3.25
		link32_PassiveHeartStatus OBJECT-TYPE
			SYNTAX INTEGER
				{
				alarm(0),
				normal(1),
				off(2),
				na(3)
				}
			MAX-ACCESS read-only
			STATUS current
			DESCRIPTION
				"get the passive heartbeat status,such as whether work in alarm mode."
			::= { link32OBP 25 }	

--  1.3.6.1.4.1.47477.10.21.32.3.26
		-- 1.3.6.1.4.1.47477.10.21.32.3.26
		link32_PowerAlarmStatus OBJECT-TYPE
			SYNTAX INTEGER
				{
				off(0),
				alarm(1),
				normal(2),
				na(3)
				}
			MAX-ACCESS read-only
			STATUS current
			DESCRIPTION
				"get whether a power alarm is generated."
			::= { link32OBP 26 }	


-- 1.3.6.1.4.1.47477.10.21.32.3.50.1
	link32_WorkModeChange 	OBJECT-TYPE    
    SYNTAX INTEGER	{
				manualMode(0),
				autoMode(1)
		}
	MAX-ACCESS read-only
	STATUS current
    DESCRIPTION
        "The Link mode Changed."
    ::= {link32OBPTrap 1}

-- 1.3.6.1.4.1.47477.10.21.32.3.50.2
	link32_StateChange 	OBJECT-TYPE    
    SYNTAX INTEGER	{
				bypass(0),
				primary(1)
		}
	MAX-ACCESS read-only
	STATUS current
    DESCRIPTION
        "The Link State(Channel) Changed."
    ::= {link32OBPTrap 2}

-- 1.3.6.1.4.1.47477.10.21.32.3.50.3
	link32_R1WaveSet 	OBJECT-TYPE    
    SYNTAX INTEGER	{
				w1310nm(0),
				w1550nm(1)
		}
	MAX-ACCESS read-only
	STATUS current
    DESCRIPTION
        "Set The link32 R1 Wave."
    ::= {link32OBPTrap 3}

-- 1.3.6.1.4.1.47477.10.21.32.3.50.4
	link32_R2WaveSet 	OBJECT-TYPE    
    SYNTAX INTEGER	{
				w1310nm(0),
				w1550nm(1)
		}
	MAX-ACCESS read-only
	STATUS current
    DESCRIPTION
        "Set The link32 R2 Wave."
    ::= {link32OBPTrap 4}			

-- 1.3.6.1.4.1.47477.10.21.32.3.50.5
	link32_R3WaveSet 	OBJECT-TYPE    
    SYNTAX INTEGER	{
				w1310nm(0),
				w1550nm(1)
		}
	MAX-ACCESS read-only
	STATUS current
    DESCRIPTION
        "Set The link32 R3 Wave."
    ::= {link32OBPTrap 5}

-- 1.3.6.1.4.1.47477.10.21.32.3.50.6
	link32_R4WaveSet 	OBJECT-TYPE    
    SYNTAX INTEGER	{
				w1310nm(0),
				w1550nm(1)
		}
	MAX-ACCESS read-only
	STATUS current
    DESCRIPTION
        "Set The link32 R4 Wave."
    ::= {link32OBPTrap 6}	
	
-- 1.3.6.1.4.1.47477.10.21.32.3.50.7
	link32_R1AlarmSet 	OBJECT-TYPE    
    SYNTAX DisplayString
	MAX-ACCESS read-only
	STATUS current
    DESCRIPTION
        "Set The link32 R1 Alarm Threshold."
    ::= {link32OBPTrap 7}

-- 1.3.6.1.4.1.47477.10.21.32.3.50.8
	link32_R2AlarmSet 	OBJECT-TYPE    
    SYNTAX DisplayString
	MAX-ACCESS read-only
	STATUS current
    DESCRIPTION
        "Set The link32 R2 Alarm Threshold."
    ::= {link32OBPTrap 8}
	
-- 1.3.6.1.4.1.47477.10.21.32.3.50.9
	link32_R3AlarmSet 	OBJECT-TYPE    
    SYNTAX DisplayString
	MAX-ACCESS read-only
	STATUS current
    DESCRIPTION
        "Set The link32 R3 Alarm Threshold."
    ::= {link32OBPTrap 9}

-- 1.3.6.1.4.1.47477.10.21.32.3.50.10
	link32_R4AlarmSet 	OBJECT-TYPE    
    SYNTAX DisplayString
	MAX-ACCESS read-only
	STATUS current
    DESCRIPTION
        "Set The link32 R4 Alarm Threshold."
    ::= {link32OBPTrap 10}	
	
	
-- 1.3.6.1.4.1.47477.10.21.32.3.50.11
	link32_1R1AlarmSet 	OBJECT-TYPE    
    SYNTAX DisplayString
	MAX-ACCESS read-only
	STATUS current
    DESCRIPTION
        "Set The link32 1R1 Alarm Threshold."
    ::= {link32OBPTrap 11}

-- 1.3.6.1.4.1.47477.10.21.32.3.50.12
	link32_2R1AlarmSet 	OBJECT-TYPE    
    SYNTAX DisplayString
	MAX-ACCESS read-only
	STATUS current
    DESCRIPTION
        "Set The link32 2R1 Alarm Threshold."
    ::= {link32OBPTrap 12}
	
-- 1.3.6.1.4.1.47477.10.21.32.3.50.13
	link32_1R2AlarmSet 	OBJECT-TYPE    
    SYNTAX DisplayString
	MAX-ACCESS read-only
	STATUS current
    DESCRIPTION
        "Set The link32 1R2 Alarm Threshold."
    ::= {link32OBPTrap 13}

-- 1.3.6.1.4.1.47477.10.21.32.3.50.14
	link32_2R2AlarmSet 	OBJECT-TYPE    
    SYNTAX DisplayString
	MAX-ACCESS read-only
	STATUS current
    DESCRIPTION
        "Set The link32 2R2 Alarm Threshold."
    ::= {link32OBPTrap 14}
	
-- 1.3.6.1.4.1.47477.10.21.32.3.50.15
	link32_1R3AlarmSet 	OBJECT-TYPE    
    SYNTAX DisplayString
	MAX-ACCESS read-only
	STATUS current
    DESCRIPTION
        "Set The link32 1R3 Alarm Threshold."
    ::= {link32OBPTrap 15}

-- 1.3.6.1.4.1.47477.10.21.32.3.50.16
	link32_2R3AlarmSet 	OBJECT-TYPE    
    SYNTAX DisplayString
	MAX-ACCESS read-only
	STATUS current
    DESCRIPTION
        "Set The link32 2R3 Alarm Threshold."
    ::= {link32OBPTrap 16}
	
-- 1.3.6.1.4.1.47477.10.21.32.3.50.17
	link32_1R4AlarmSet 	OBJECT-TYPE    
    SYNTAX DisplayString
	MAX-ACCESS read-only
	STATUS current
    DESCRIPTION
        "Set The link32 1R4 Alarm Threshold."
    ::= {link32OBPTrap 17}

-- 1.3.6.1.4.1.47477.10.21.32.3.50.18
	link32_2R4AlarmSet 	OBJECT-TYPE    
    SYNTAX DisplayString
	MAX-ACCESS read-only
	STATUS current
    DESCRIPTION
        "Set The link32 2R4 Alarm Threshold."
    ::= {link32OBPTrap 18}
	
-- 1.3.6.1.4.1.47477.10.21.32.3.50.19
	link32_PowerAlarmBypass2Changed 	OBJECT-TYPE    
    SYNTAX INTEGER
				{
				off(0),
				powerAlarmR1(1),
				powerAlarmR2(2),
				anyAlarmR1-R2(3),
				allAlarmR1-R2(4)
				}
	MAX-ACCESS read-only
	STATUS current
    DESCRIPTION
        "The link32 PowerAlarmBypass2 Changed."
    ::= {link32OBPTrap 19}
	
-- 1.3.6.1.4.1.47477.10.21.32.3.50.20
	link32_PowerAlarmBypass4Changed 	OBJECT-TYPE    
    SYNTAX INTEGER
				{
				off(0),
				powerAlarmR1(1),
				powerAlarmR2(2),
				powerAlarmR3(3),
				powerAlarmR4(4),
				anyAlarmR1-R4(5),
				allAlarmR1-R4(6)
				}
	MAX-ACCESS read-only
	STATUS current
    DESCRIPTION
        "The link32 PowerAlarmBypass4 Changed."
    ::= {link32OBPTrap 20}	
	
-- 1.3.6.1.4.1.47477.10.21.32.3.50.21
	link32_PowerAlarmBypass8Changed 	OBJECT-TYPE    
    SYNTAX INTEGER
				{
				off(0),
				powerAlarm1R1(1),
				powerAlarm1R2(3),
				powerAlarm1R3(5),
				powerAlarm1R4(7),
				powerAlarm2R1(2),
				powerAlarm2R2(4),
				powerAlarm2R3(6),
				powerAlarm2R4(8),
				anyAlarm1R1-2R4(9),
				allAlarm1R1-2R4(10)
				}
	MAX-ACCESS read-only
	STATUS current
    DESCRIPTION
        "The link32 PowerAlarmBypass8 Changed."
    ::= {link32OBPTrap 21}
	
-- 1.3.6.1.4.1.47477.10.21.32.3.50.22
	link32_powerAlarmR1 	OBJECT-TYPE    
    SYNTAX DisplayString
	MAX-ACCESS read-only
	STATUS current
    DESCRIPTION
        "Set The link32 R1 Power Status Alarm."
    ::= {link32OBPTrap 22}
	
-- 1.3.6.1.4.1.47477.10.21.32.3.50.23
	link32_powerAlarmR2 	OBJECT-TYPE    
    SYNTAX DisplayString
	MAX-ACCESS read-only
	STATUS current
    DESCRIPTION
        "Set The link32 R2 Power Status Alarm."
    ::= {link32OBPTrap 23}
	
-- 1.3.6.1.4.1.47477.10.21.32.3.50.24
	link32_powerAlarmR3 	OBJECT-TYPE    
    SYNTAX DisplayString
	MAX-ACCESS read-only
	STATUS current
    DESCRIPTION
        "Set The link32 R3 Power Status Alarm."
    ::= {link32OBPTrap 24}
	
-- 1.3.6.1.4.1.47477.10.21.32.3.50.25
	link32_powerAlarmR4 	OBJECT-TYPE    
    SYNTAX DisplayString
	MAX-ACCESS read-only
	STATUS current
    DESCRIPTION
        "Set The link32 R4 Power Status Alarm."
    ::= {link32OBPTrap 25}
	
	
-- 1.3.6.1.4.1.47477.10.21.32.3.50.26
	link32_powerAlarm1R1 	OBJECT-TYPE    
    SYNTAX DisplayString
	MAX-ACCESS read-only
	STATUS current
    DESCRIPTION
        "Set The link32 1R1 Power Status Alarm."
    ::= {link32OBPTrap 26}
	
-- 1.3.6.1.4.1.47477.10.21.32.3.50.27
	link32_powerAlarm2R1 	OBJECT-TYPE    
    SYNTAX DisplayString
	MAX-ACCESS read-only
	STATUS current
    DESCRIPTION
        "Set The link32 2R1 Power Status Alarm."
    ::= {link32OBPTrap 27}
	
-- 1.3.6.1.4.1.47477.10.21.32.3.50.28
	link32_powerAlarm1R2 	OBJECT-TYPE    
    SYNTAX DisplayString
	MAX-ACCESS read-only
	STATUS current
    DESCRIPTION
        "Set The link32 1R2 Power Status Alarm."
    ::= {link32OBPTrap 28}
	
-- 1.3.6.1.4.1.47477.10.21.32.3.50.29
	link32_powerAlarm2R2 	OBJECT-TYPE    
    SYNTAX DisplayString
	MAX-ACCESS read-only
	STATUS current
    DESCRIPTION
        "Set The link32 2R2 Power Status Alarm."
    ::= {link32OBPTrap 29}
	
-- 1.3.6.1.4.1.47477.10.21.32.3.50.30
	link32_powerAlarm1R3 	OBJECT-TYPE    
    SYNTAX DisplayString
	MAX-ACCESS read-only
	STATUS current
    DESCRIPTION
        "Set The link32 1R3 Power Status Alarm."
    ::= {link32OBPTrap 30}
	
-- 1.3.6.1.4.1.47477.10.21.32.3.50.31
	link32_powerAlarm2R3 	OBJECT-TYPE    
    SYNTAX DisplayString
	MAX-ACCESS read-only
	STATUS current
    DESCRIPTION
        "Set The link32 2R1 Power Status Alarm."
    ::= {link32OBPTrap 31}
	
-- 1.3.6.1.4.1.47477.10.21.32.3.50.32
	link32_powerAlarm1R4 	OBJECT-TYPE    
    SYNTAX DisplayString
	MAX-ACCESS read-only
	STATUS current
    DESCRIPTION
        "Set The link32 1R4 Power Status Alarm."
    ::= {link32OBPTrap 32}
	
-- 1.3.6.1.4.1.47477.10.21.32.3.50.33
	link32_powerAlarm2R4 	OBJECT-TYPE    
    SYNTAX DisplayString
	MAX-ACCESS read-only
	STATUS current
    DESCRIPTION
        "Set The link32 2R4 Power Status Alarm."
    ::= {link32OBPTrap 33}



	END

--
-- OTS3000-NMU.my
--
